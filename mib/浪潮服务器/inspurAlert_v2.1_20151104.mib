--/************************************************************************ 
--*                                                                       * 
--*  Copyright (c) 1998-2004 Intel Corporation. All Rights Reserved.      * 
--*                                                                       * 
--* Redistribution and use in source and binary forms, with or without    * 
--* modification, are permitted provided that the following conditions    * 
--* are met:                                                              * 
--*                                                                       * 
--*   a.. Redistributions of source code must retain the above copyright  * 
--*       notice, this list of conditions and the following disclaimer.   * 
--*   b.. Redistributions in binary form must reproduce the above         * 
--*       copyright notice, this list of conditions and the following     * 
--*       disclaimer in the documentation and/or other materials provided * 
--*       with the distribution.                                          * 
--*   c.. Neither the name of Intel Corporation nor the names of its      * 
--*       contributors may be used to endorse or promote products derived * 
--*       from this software without specific prior written permission.   * 
--*                                                                       * 
--* THIS SOFTWARE IS PROVIDED BY THE COPYRIGHT HOLDERS AND CONTRIBUTORS   * 
--* "AS IS" AND ANY EXPRESS OR IMPLIED WARRANTIES, INCLUDING, BUT NOT     * 
--* LIMITED TO, THE IMPLIED WARRANTIES OF MERCHANTABILITY AND FITNESS FOR * 
--* A PARTICULAR PURPOSE ARE DISCLAIMED. IN NO EVENT SHALL THE COPYRIGHT  * 
--* OWNER OR CONTRIBUTORS BE LIABLE FOR ANY DIRECT, INDIRECT, INCIDENTAL, * 
--* SPECIAL, EXEMPLARY, OR CONSEQUENTIAL DAMAGES (INCLUDING, BUT NOT      * 
--* LIMITED TO, PROCUREMENT OF SUBSTITUTE GOODS OR SERVICES; LOSS OF USE, * 
--* DATA, OR PROFITS; OR BUSINESS INTERRUPTION) HOWEVER CAUSED AND ON     * 
--* ANY THEORY OF LIABILITY, WHETHER IN CONTRACT, STRICT LIABILITY, OR    * 
--* TORT (INCLUDING NEGLIGENCE OR OTHERWISE) ARISING IN ANY WAY OUT OF    * 
--* THE USE OF THIS SOFTWARE, EVEN IF ADVISED OF THE POSSIBILITY OF SUCH  * 
--* DAMAGE.                                                               * 
--*                                                                       * 
--************************************************************************* 
--* Name                        : PetEvents.mib 
--* Description	                : MIB file for PET events 
--* Created                     : Wesdnesday, December 17, 2003 
--* Author                      : Intel Corporation 
--*  
--* $History:$  
--* 
--*             Date                    : March 7th,2002  
--*             Changed by              :  
--*             Change Description      : Updated MIB file  
--*							   
--*             Date                    : December 17th,2003  
--*             Changed by              :  
--*             Change Description      : Started with ASF MIB file 
--*                                        
--*************************************************************************/ 

--******************************************************************* 
--******************************************************************** 
--****                                                              ** 
--****    (C)Copyright 2011-2012, American Megatrends Inc.          ** 
--****                                                              ** 
--****    All Rights Reserved.                                      ** 
--****                                                              ** 
--****    5555 , Oakbrook Pkwy, Norcross,                           ** 
--****                                                              ** 
--****    Georgia - 30093, USA. Phone-(770)-246-8600.               ** 
--****                                                              ** 
--******************************************************************** 
--******************************************************************** 
--* Name                        : PETTrap.mib 
--* Description	                : Contains MIB for all standard sensor types 
--* Created                     : 8th August, 2011 
--* Author                      : AMI 
--*                                        
--*************************************************************************/ 

--********************************************************************************************
--Release Note:
--version  time		author   	note
--v1.0     20110808     AMI      	Contains MIB for all standard sensor types 
--v1.1     20140801     Inspur-wxl	add immtrapg and its children
--v1.2	   20141010     Inspur-wxl	fix insert hdd alert remove, remove hdd alert insert.
--v1.3     20141021	Inspur-wxl	add oem MemError and CPUERROR; modify enterprises id from 3183 to 37945
--v1.4	   20150310	Inspur-wxl	Remove "_", for linux cmd line error to load mib.
--v2.1	   20151104	Inspur-wxl	support v1/v2/v3.
--********************************************************************************************/ 
PET-EVENTS DEFINITIONS ::=  BEGIN 

	IMPORTS 
		enterprises 
			FROM RFC1155-SMI 
		OBJECT-TYPE 
			FROM RFC-1212 

       	TRAP-TYPE 
		        FROM RFC-1215 
  

		DisplayString 
			FROM RFC1213-MIB; 

	wiredformgmt     OBJECT IDENTIFIER ::=  { enterprises 37945 } 
	pet              OBJECT IDENTIFIER ::=  { wiredformgmt 1 } 

-- MODULE IDENTIFICATION 
-- 
--  PET Events Alerting MODULE-IDENTITY 
--  LAST-UPDATED "February 4, 2004" 
--  ORGANIZATION "Intel Corporation" 
--  CONTACT-INFO 
--   " PET Events, 
--     Intel Corporation, DP3-407 
--	   DuPont, WA 98352" 
--  DESCRIPTION 
--  "This is the MIB file for SNMPv1.0 based PET traps" 


-- **************************************** 
-- SYSTEM INFORMATION BRANCH STARTS HERE. 
-- **************************************** 

	petevts   		OBJECT IDENTIFIER ::=  { pet 1 } 



-- wiredformgmt = .1.3.6.1.4.1.37945 
-- pet=.1.3.6.1.4.1.37945.1 
-- petevts = .1.3.6.1.4.1.37945.1.1 

	immtrapg  		OBJECT IDENTIFIER ::=  { petevts 1 }
 --.1.3.6.1.4.1.37945.1.1.1 

        altTrapTime      OBJECT-TYPE
                       SYNTAX  DisplayString
                       ACCESS  read-only
                       STATUS  mandatory
                       DESCRIPTION
                       "Timestamp of Local Date and Time when alert was generated"
                       ::=  { immtrapg 1 }
--.1.3.6.1.4.1.37945.1.1.1.1 

        altSpTxtId        OBJECT-TYPE
                       SYNTAX  DisplayString
                       ACCESS  read-only
                       STATUS  mandatory
                       DESCRIPTION
                       "SP System Identification - Text Identification"
                       ::=  { immtrapg 3 }

        altSysUuid     OBJECT-TYPE
                       SYNTAX  DisplayString
                       ACCESS  read-only
                       STATUS  mandatory
                       DESCRIPTION
                       "Host System UUID(Universal Unique ID)"
                       ::=  { immtrapg 5 }
                       
        altSysSern     OBJECT-TYPE
                       SYNTAX  DisplayString
                       ACCESS  read-only
                       STATUS  mandatory
                       DESCRIPTION
                       "Host System Serial Number"
                       ::=  { immtrapg 6 }
        
        altPriority     OBJECT-TYPE
                       SYNTAX  INTEGER (0..65535)
                       ACCESS  read-only
                       STATUS  mandatory
                       DESCRIPTION
                       "Alert Severity Value
                          - Information(0)
                          - Warning(1)
                          - Critical(2)
                          - Recovery(8)"
                       ::=  { immtrapg 8 }

        altMsgText     OBJECT-TYPE
                       SYNTAX  DisplayString
                       ACCESS  read-only
                       STATUS  mandatory
                       DESCRIPTION
                       "Alert Message Text"
                       ::=  { immtrapg 9 }

        altMsgID       OBJECT-TYPE
                       SYNTAX  INTEGER
                       ACCESS  read-only
                       STATUS  mandatory
                       DESCRIPTION
                       "Alert Message ID"
                       ::=  { immtrapg 10 }

        altMsgIDPrefix OBJECT-TYPE
                       SYNTAX  DisplayString
                       ACCESS  read-only
                       STATUS  mandatory
                       DESCRIPTION
                       "Alert Message ID"
                       ::=  { immtrapg 11 }	
                       
				   
        altHostContact  OBJECT-TYPE
                       SYNTAX  DisplayString
                       ACCESS  read-only
                       STATUS  mandatory
                       DESCRIPTION
                       "Host Contact"
                       ::=  { immtrapg 12 }

        altHostLocation  OBJECT-TYPE
                       SYNTAX  DisplayString
                       ACCESS  read-only
                       STATUS  mandatory
                       DESCRIPTION
                       "Host Location"
                       ::=  { immtrapg 13 }

        altHostRoomID  OBJECT-TYPE
                       SYNTAX  DisplayString
                       ACCESS  read-only
                       STATUS  mandatory
                       DESCRIPTION
                       "Host Location - Room ID"
                       ::=  { immtrapg 14 }

        altHostRackID  OBJECT-TYPE
                       SYNTAX  DisplayString
                       ACCESS  read-only
                       STATUS  mandatory
                       DESCRIPTION
                       "Host Location - Rack ID"
                       ::=  { immtrapg 15 }

        altHostLowestUpos  OBJECT-TYPE
                       SYNTAX  DisplayString
                       ACCESS  read-only
                       STATUS  mandatory
                       DESCRIPTION
                       "Host Location - Lowest U-position"
                       ::=  { immtrapg 16 }

        altHostBladeBay  OBJECT-TYPE
                       SYNTAX  DisplayString
                       ACCESS  read-only
                       STATUS  mandatory
                       DESCRIPTION
                       "Host Location - BladeBay"
                       ::=  { immtrapg 17 }

        altEventID     OBJECT-TYPE
                       SYNTAX  DisplayString
                       ACCESS  read-only
                       STATUS  mandatory
                       DESCRIPTION
                       "Event Identifier"
                       ::=  { immtrapg 18 }

        altServiceable OBJECT-TYPE
                       SYNTAX  INTEGER {
                       notServiceable(0),
                       serviceableByIBM(1),
                       serviceableByCustomer(2)
                       }
                       ACCESS  read-only
                       STATUS  mandatory
                       DESCRIPTION
                       "Serviceability information."
                       ::=  { immtrapg 19 }

        altTest        OBJECT-TYPE
                       SYNTAX  INTEGER {
                       false(0),
                       true(1)
                       }
                       ACCESS  read-only
                       STATUS  mandatory
                       DESCRIPTION
                       "This event generated for test purposes."
                       ::=  { immtrapg 20 }

        altFailingFRUs OBJECT-TYPE
                       SYNTAX  DisplayString
                       ACCESS  read-only
                       STATUS  mandatory
                       DESCRIPTION
                       "Ordered list of Failing FRU Numbers, separated by commas."
                       ::=  { immtrapg 21 }

        altHostMTM     OBJECT-TYPE
                       SYNTAX  DisplayString
                       ACCESS  read-only
                       STATUS  mandatory
                       DESCRIPTION
                       "Machine Type and Model for failing host."
                       ::=  { immtrapg 22 }

        altAuxData     OBJECT-TYPE
                       SYNTAX  DisplayString
                       ACCESS  read-only
                       STATUS  mandatory
                       DESCRIPTION
                       "Auxiliary data that may be included for some events."
                       ::=  { immtrapg 23 }


       altSysManufacture   OBJECT-TYPE 
                      SYNTAX  DisplayString 
                      ACCESS  read-only 
                      STATUS  mandatory 
                      DESCRIPTION 
                      "Manufacture name" 
                      ::=  { immtrapg 24 } 


       altSysModel        OBJECT-TYPE 
                      SYNTAX  DisplayString 
                      ACCESS  read-only 
                      STATUS  mandatory 
                      DESCRIPTION 
                      "System model" 
                      ::=  { immtrapg 25 } 

       altSensorName        OBJECT-TYPE 
                      SYNTAX  DisplayString 
                      ACCESS  read-only 
                      STATUS  mandatory 
                      DESCRIPTION 
                      "Sensor Name" 
                      ::=  { immtrapg 26 } 

       altSensorType     OBJECT-TYPE 
                      SYNTAX  DisplayString 
                      ACCESS  read-only 
                      STATUS  mandatory 
                      DESCRIPTION 
                      "Sensor Type" 
                      ::=  { immtrapg 27 }

       altSensorReading  OBJECT-TYPE 
                      SYNTAX  DisplayString 
                      ACCESS  read-only 
                      STATUS  mandatory 
                      DESCRIPTION 
                      "Current Sensor Reading" 
                      ::=  { immtrapg 28 }  

      altSensorThreshold OBJECT-TYPE 
                      SYNTAX  DisplayString 
                      ACCESS  read-only 
                      STATUS  mandatory 
                      DESCRIPTION 
                      "Sensor Threshold: LowerNonRecoverable, LowerCritical, LowerNonCritical, UpperNonCritical, UpperCritical, UpperNonRecoverable" 
                      ::=  { immtrapg 29 }  

       altHostOS       OBJECT-TYPE 
                      SYNTAX  DisplayString 
                      ACCESS  read-only 
                      STATUS  mandatory 
                      DESCRIPTION 
                      "Host OS" 
                      ::=  { immtrapg 32 } 


       altSysboard	      OBJECT-TYPE 
                      SYNTAX  DisplayString 
                      ACCESS  read-only 
                      STATUS  mandatory 
                      DESCRIPTION 
                      "Board name." 
                      ::=  { immtrapg 33 } 

       altSysboardType      OBJECT-TYPE 
                      SYNTAX  DisplayString 
                      ACCESS  read-only 
                      STATUS  mandatory 
                      DESCRIPTION 
                      "Board Type" 
                      ::=  { immtrapg 34 } 

       altSysboardstatus     OBJECT-TYPE 
                      SYNTAX  DisplayString 
                      ACCESS  read-only 
                      STATUS  mandatory 
                      DESCRIPTION 
                      "Board Status" 
                      ::=  { immtrapg 35 } 

       altSysName     OBJECT-TYPE 
                      SYNTAX  DisplayString 
                      ACCESS  read-only 
                      STATUS  mandatory 
                      DESCRIPTION 
                      "System Name" 
                      ::=  { immtrapg 36 } 
					  
					  
					  
-- ********************************************** 
-- *		Test			* 
-- ********************************************** 
TrapV2cV3Test NOTIFICATION-TYPE 
STATUS current
-- ENTERPRISE petevts 
DESCRIPTION  
"Trap Test for v2c, v3" 
::= { petevts 0 }

TrapV1Test TRAP-TYPE 
ENTERPRISE petevts 
DESCRIPTION  
 "Trap Test for v1" 
::= 0

-- ********************************************** 
-- *		Temperature			* 
-- ********************************************** 

-- Temperature has decreased below lower non-critical threshold 
trapUnderTemperatureWarningLow NOTIFICATION-TYPE 
STATUS current
-- ENTERPRISE petevts 
DESCRIPTION  
"Under-Temperature Warning (Lower non-critical, going low)" 

--#TYPE       "Temperature Event" 
--#SUMMARY    "Under-Temperature Warning (Lower non-critical, going low)" 
--#ARGUMENTS  {} 
--#SEVERITY   WARNING 

::= { petevts 65792 }
 
-- Temperature has increased above lower non-critical threshold 
trapUnderTemperatureWarningHigh NOTIFICATION-TYPE 
STATUS current
-- ENTERPRISE petevts 
DESCRIPTION  
"Under-Temperature Warning (Lower non-critical, going high)" 

--#TYPE       "Temperature Event" 
--#SUMMARY    "Under-Temperature Warning (Lower non-critical, going high)" 
--#ARGUMENTS  {} 
--#SEVERITY   WARNING 

::= { petevts 65793 }
 
-- Temperature has decreased below lower critical threshold 
trapUnderTemperatureCriticalLow NOTIFICATION-TYPE 
STATUS current
-- ENTERPRISE petevts 
DESCRIPTION  
"Critical Under-Temperature problem (Lower critical, going low)" 

--#TYPE       "Temperature Event" 
--#SUMMARY    "Under-Temperature Warning (Lower critical, going low)" 
--#ARGUMENTS  {} 
--#SEVERITY   CRITICAL 

::= { petevts 65794 }
 
 -- Temperature has increased above lower critical threshold 
trapUnderTemperatureCriticalHigh NOTIFICATION-TYPE 
STATUS current
-- ENTERPRISE petevts 
DESCRIPTION  
"Critical Under-Temperature problem (Lower critical, going high)" 

--#TYPE       "Temperature Event" 
--#SUMMARY    "Under-Temperature Warning (Lower critical, going high)" 
--#ARGUMENTS  {} 
--#SEVERITY   CRITICAL 

::= { petevts 65795 }
 
 -- Temperature has decreased below lower non-recoverable threshold 
trapUnderTemperatureNonRecoverableLow NOTIFICATION-TYPE 
STATUS current
-- ENTERPRISE petevts 
DESCRIPTION  
"Critical Under-Temperature problem (Lower non-recoverable, going low)" 

--#TYPE       "Temperature Event" 
--#SUMMARY    "Under-Temperature Warning (Lower non-recoverable, going low)" 
--#ARGUMENTS  {} 
--#SEVERITY   CRITICAL 

::= { petevts 65796 }
 
 -- Temperature has increased above lower non-recoverable threshold 
trapUnderTemperatureNonRecoverableHigh NOTIFICATION-TYPE 
STATUS current
-- ENTERPRISE petevts 
DESCRIPTION  
"Critical Under-Temperature problem (Lower non-recoverable, going high)" 

--#TYPE       "Temperature Event" 
--#SUMMARY    "Under-Temperature Warning (Lower non-recoverable, going high)" 
--#ARGUMENTS  {} 
--#SEVERITY   CRITICAL 

::= { petevts 65797 }
 
-- Temperature has decreased below Upper non-critical threshold 
trapOverTemperatureWarningLow NOTIFICATION-TYPE 
STATUS current
-- ENTERPRISE petevts 
DESCRIPTION  
"Over-Temperature Warning (Upper non-critical, going low)" 

--#TYPE       "Temperature Event" 
--#SUMMARY    "Over-Temperature Warning (Upper non-critical, going low)" 
--#ARGUMENTS  {} 
--#SEVERITY   WARNING 

::= { petevts 65798 }
 
-- Temperature has increased above upper non-critical threshold. 
trapOverTemperatureWarningHigh NOTIFICATION-TYPE 
STATUS current
-- ENTERPRISE petevts 
DESCRIPTION  
"Over-Temperature Warning (Upper non-critical, going high)" 

--#TYPE       "Temperature Event" 
--#SUMMARY    "Over-Temperature Warning (Upper non-critical, going high)" 
--#ARGUMENTS  {} 
--#SEVERITY   WARNING 

::= { petevts 65799 }
 
-- Temperature has decreased below Upper critical threshold 
trapOverTemperatureCriticalLow NOTIFICATION-TYPE 
STATUS current
-- ENTERPRISE petevts 
DESCRIPTION  
"Critical Over-Temperature problem (Upper critical, going low)" 

--#TYPE       "Temperature Event" 
--#SUMMARY    "Over-Temperature Warning (Upper critical, going low)" 
--#ARGUMENTS  {} 
--#SEVERITY   CRITICAL 

::= { petevts 65800 }
 
 -- Temperature has increased above Upper critical threshold 
trapOverTemperatureCriticalHigh NOTIFICATION-TYPE 
STATUS current
-- ENTERPRISE petevts 
DESCRIPTION  
"Critical Over-Temperature problem (Upper critical, going high)" 

--#TYPE       "Temperature Event" 
--#SUMMARY    "Over-Temperature Warning (Upper critical, going high)" 
--#ARGUMENTS  {} 
--#SEVERITY   CRITICAL 

::= { petevts 65801 }
 
 -- Temperature has decreased below Upper non-recoverable threshold 
trapOverTemperatureNonRecoverableLow NOTIFICATION-TYPE 
STATUS current
-- ENTERPRISE petevts 
DESCRIPTION  
"Critical Over-Temperature problem (Upper non-recoverable, going low)" 

--#TYPE       "Temperature Event" 
--#SUMMARY    "Over-Temperature Warning (Upper non-recoverable, going low)" 
--#ARGUMENTS  {} 
--#SEVERITY   CRITICAL 

::= { petevts 65802 }
 
 -- Temperature has increased above Upper non-recoverable threshold 
trapOverTemperatureNonRecoverableHigh NOTIFICATION-TYPE 
STATUS current
-- ENTERPRISE petevts 
DESCRIPTION  
"Critical Over-Temperature problem (Upper non-recoverable, going high)" 

--#TYPE       "Temperature Event" 
--#SUMMARY    "Under-Temperature Warning (Upper non-recoverable, going high)" 
--#ARGUMENTS  {} 
--#SEVERITY   CRITICAL 

::= { petevts 65803 }
 
-- Temperature decreased below lower non-critical threshold Cleared 
trapUnderTemperatureWarningLowCleared NOTIFICATION-TYPE 
STATUS current
-- ENTERPRISE petevts 
DESCRIPTION  
"Under-Temperature Warning (Lower non-critical, going low) Cleared" 

--#TYPE       "Temperature Event" 
--#SUMMARY    "Under-Temperature Warning (Lower non-critical, going low) Cleared" 
--#ARGUMENTS  {} 
--#SEVERITY   INFORMATIONAL 

::= { petevts 65920 }
 
-- Temperature increased above lower non-critical threshold Cleared 
trapUnderTemperatureWarningHighCleared NOTIFICATION-TYPE 
STATUS current
-- ENTERPRISE petevts 
DESCRIPTION  
"Under-Temperature Warning (Lower non-critical, going high)Cleared" 

--#TYPE       "Temperature Event" 
--#SUMMARY    "Under-Temperature Warning (Lower non-critical, going high)Cleared" 
--#ARGUMENTS  {} 
--#SEVERITY   INFORMATIONAL 

::= { petevts 65921 }
 
-- Temperature decreased below lower critical threshold Cleared 
trapUnderTemperatureCriticalLowCleared NOTIFICATION-TYPE 
STATUS current
-- ENTERPRISE petevts 
DESCRIPTION  
"Critical Under-Temperature problem (Lower critical, going low)Cleared" 

--#TYPE       "Temperature Event" 
--#SUMMARY    "Under-Temperature Warning (Lower critical, going low)Cleared" 
--#ARGUMENTS  {} 
--#SEVERITY   INFORMATIONAL 

::= { petevts 65922 }
 
 -- Temperature increased above lower critical threshold Cleared 
trapUnderTemperatureCriticalHighCleared NOTIFICATION-TYPE 
STATUS current
-- ENTERPRISE petevts 
DESCRIPTION  
"Critical Under-Temperature problem (Lower critical, going high) Cleared" 

--#TYPE       "Temperature Event" 
--#SUMMARY    "Under-Temperature Warning (Lower critical, going high) Cleared" 
--#ARGUMENTS  {} 
--#SEVERITY   INFORMATIONAL 

::= { petevts 65923 }
 
 -- Temperature decreased below lower non-recoverable threshold Cleared 
trapUnderTemperatureNonRecoverableLowCleared NOTIFICATION-TYPE 
STATUS current
-- ENTERPRISE petevts 
DESCRIPTION  
"Critical Under-Temperature problem (Lower non-recoverable, going low)Cleared" 

--#TYPE       "Temperature Event" 
--#SUMMARY    "Under-Temperature Warning (Lower non-recoverable, going low)Cleared" 
--#ARGUMENTS  {} 
--#SEVERITY   INFORMATIONAL 

::= { petevts 65924 }
 
 -- Temperature increased above lower non-recoverable threshold Cleared 
trapUnderTemperatureNonRecoverableHighCleared NOTIFICATION-TYPE 
STATUS current
-- ENTERPRISE petevts 
DESCRIPTION  
"Critical Under-Temperature problem (Lower non-recoverable, going high) Cleared" 

--#TYPE       "Temperature Event" 
--#SUMMARY    "Under-Temperature Warning (Lower non-recoverable, going high) Cleared" 
--#ARGUMENTS  {} 
--#SEVERITY   INFORMATIONAL 

::= { petevts 65925 }
 
-- Temperature decreased below Upper non-critical threshold Cleared 
trapOverTemperatureWarningLowCleared NOTIFICATION-TYPE 
STATUS current
-- ENTERPRISE petevts 
DESCRIPTION  
"Over-Temperature Warning (Upper non-critical, going low) Cleared" 

--#TYPE       "Temperature Event" 
--#SUMMARY    "Over-Temperature Warning (Upper non-critical, going low) Cleared" 
--#ARGUMENTS  {} 
--#SEVERITY   INFORMATIONAL 

::= { petevts 65926 }
 
-- Temperature increased above upper non-critical threshold Cleared 
trapOverTemperatureWarningHighCleared NOTIFICATION-TYPE 
STATUS current
-- ENTERPRISE petevts 
DESCRIPTION  
"Over-Temperature Warning (Upper non-critical, going high)Cleared" 

--#TYPE       "Temperature Event" 
--#SUMMARY    "Over-Temperature Warning (Upper non-critical, going high)Cleared" 
--#ARGUMENTS  {} 
--#SEVERITY   INFORMATIONAL 

::= { petevts 65927 }
 
-- Temperature decreased below Upper critical threshold Cleared 
trapOverTemperatureCriticalLowCleared NOTIFICATION-TYPE 
STATUS current
-- ENTERPRISE petevts 
DESCRIPTION  
"Critical Over-Temperature problem (Upper critical, going low) Cleared" 

--#TYPE       "Temperature Event" 
--#SUMMARY    "Over-Temperature Warning (Upper critical, going low) Cleared" 
--#ARGUMENTS  {} 
--#SEVERITY   INFORMATIONAL 

::= { petevts 65928 }
 
 -- Temperature increased above Upper critical threshold Cleared 
trapOverTemperatureCriticalHighCleared NOTIFICATION-TYPE 
STATUS current
-- ENTERPRISE petevts 
DESCRIPTION  
"Critical Over-Temperature problem (Upper critical, going high)Cleared" 

--#TYPE       "Temperature Event" 
--#SUMMARY    "Over-Temperature Warning (Upper critical, going high)Cleared" 
--#ARGUMENTS  {} 
--#SEVERITY   INFORMATIONAL 

::= { petevts 65929 }
 
 -- Temperature decreased below Upper non-recoverable threshold Cleared 
trapOverTemperatureNonRecoverableLowCleared NOTIFICATION-TYPE 
STATUS current
-- ENTERPRISE petevts 
DESCRIPTION  
"Critical Over-Temperature problem (Upper non-recoverable, going low)Cleared" 

--#TYPE       "Temperature Event" 
--#SUMMARY    "Over-Temperature Warning (Upper non-recoverable, going low)Cleared" 
--#ARGUMENTS  {} 
--#SEVERITY   INFORMATIONAL 

::= { petevts 65930 }
 
 -- Temperature increased above Upper non-recoverable threshold Cleared 
trapOverTemperatureNonRecoverableHighCleared NOTIFICATION-TYPE 
STATUS current
-- ENTERPRISE petevts 
DESCRIPTION  
"Critical Over-Temperature problem (Upper non-recoverable, going high) Cleared" 

--#TYPE       "Temperature Event" 
--#SUMMARY    "Under-Temperature Warning (Upper non-recoverable, going high) Cleared" 
--#ARGUMENTS  {} 
--#SEVERITY   INFORMATIONAL 

::= { petevts 65931 }
 
-- Generic critical temperature problem 
trapGenericCriticalTemperature NOTIFICATION-TYPE 
STATUS current
-- ENTERPRISE petevts 
DESCRIPTION  
"Generic Critical Temperature Problem (Transition to Critical from less severe)" 

--#TYPE       "Temperature Event" 
--#SUMMARY    "Generic Critical Temperature Problem (Transition to Critical from less severe)" 
--#ARGUMENTS  {} 
--#SEVERITY   CRITICAL 

::= { petevts 67330 }

-- Generic temperature warning 
trapGenericTemperatureWarning NOTIFICATION-TYPE 
STATUS current
-- ENTERPRISE petevts 
DESCRIPTION  
 "Generic Temperature Warning (Transition to Warning from less severe)" 

--#TYPE	      "Temperature Event" 
--#SUMMARY    "Generic Temperature Warning (Transition to Warning from less severe)" 
--#ARGUMENTS  {} 
--#SEVERITY   WARNING 

::= { petevts 67331 }
 
-- ********************************************** 
-- *		Voltage			* 
-- ********************************************** 

-- Voltage has decreased below lower non-critical threshold 
trapUnderVoltageWarningLow NOTIFICATION-TYPE 
STATUS current
-- ENTERPRISE petevts 
DESCRIPTION  
"Under-Voltage Warning (Lower non-critical, going low)" 

--#TYPE       "Voltage Event" 
--#SUMMARY    "Under-Voltage Warning (Lower non-critical, going low)" 
--#ARGUMENTS  {} 
--#SEVERITY   WARNING 

::= { petevts 131328 }
 
-- Voltage has increased above lower non-critical threshold 
trapUnderVoltageWarningHigh NOTIFICATION-TYPE 
STATUS current
-- ENTERPRISE petevts 
DESCRIPTION  
"Under-Voltage Warning (Lower non-critical, going high)" 

--#TYPE       "Voltage Event" 
--#SUMMARY    "Under-Voltage Warning (Lower non-critical, going high)" 
--#ARGUMENTS  {} 
--#SEVERITY   WARNING 

::= { petevts 131329 }
 
-- Voltage has decreased below lower critical threshold 
trapUnderVoltageCriticalLow NOTIFICATION-TYPE 
STATUS current
-- ENTERPRISE petevts 
DESCRIPTION  
"Critical Under-Voltage problem (Lower critical, going low)" 

--#TYPE       "Voltage Event" 
--#SUMMARY    "Under-Voltage Warning (Lower critical, going low)" 
--#ARGUMENTS  {} 
--#SEVERITY   CRITICAL 

::= { petevts 131330 }
 
 -- Voltage has increased above lower critical threshold 
trapUnderVoltageCriticalHigh NOTIFICATION-TYPE 
STATUS current
-- ENTERPRISE petevts 
DESCRIPTION  
"Critical Under-Voltage problem (Lower critical, going high)" 

--#TYPE       "Voltage Event" 
--#SUMMARY    "Under-Voltage Warning (Lower critical, going high)" 
--#ARGUMENTS  {} 
--#SEVERITY   CRITICAL 

::= { petevts 131331 }
 
 -- Voltage has decreased below lower non-recoverable threshold 
trapUnderVoltageNonRecoverableLow NOTIFICATION-TYPE 
STATUS current
-- ENTERPRISE petevts 
DESCRIPTION  
"Critical Under-Voltage problem (Lower non-recoverable, going low)" 

--#TYPE       "Voltage Event" 
--#SUMMARY    "Under-Voltage Warning (Lower non-recoverable, going low)" 
--#ARGUMENTS  {} 
--#SEVERITY   CRITICAL 

::= { petevts 131332 }
 
 -- Voltage has increased above lower non-recoverable threshold 
trapUnderVoltageNonRecoverableHigh NOTIFICATION-TYPE 
STATUS current
-- ENTERPRISE petevts 
DESCRIPTION  
"Critical Under-Voltage problem (Lower non-recoverable, going high)" 

--#TYPE       "Voltage Event" 
--#SUMMARY    "Under-Voltage Warning (Lower non-recoverable, going high)" 
--#ARGUMENTS  {} 
--#SEVERITY   CRITICAL 

::= { petevts 131333 }
 
-- Voltage has decreased below Upper non-critical threshold 
trapOverVoltageWarningLow NOTIFICATION-TYPE 
STATUS current
-- ENTERPRISE petevts 
DESCRIPTION  
"Over-Voltage Warning (Upper non-critical, going low)" 

--#TYPE       "Voltage Event" 
--#SUMMARY    "Over-Voltage Warning (Upper non-critical, going low)" 
--#ARGUMENTS  {} 
--#SEVERITY   WARNING 

::= { petevts 131334 }
 
-- Voltage has increased above upper non-critical threshold. 
trapOverVoltageWarningHigh NOTIFICATION-TYPE 
STATUS current
-- ENTERPRISE petevts 
DESCRIPTION  
"Over-Voltage Warning (Upper non-critical, going high)" 

--#TYPE       "Voltage Event" 
--#SUMMARY    "Over-Voltage Warning (Upper non-critical, going high)" 
--#ARGUMENTS  {} 
--#SEVERITY   WARNING 

::= { petevts 131335 }
 
-- Voltage has decreased below Upper critical threshold 
trapOverVoltageCriticalLow NOTIFICATION-TYPE 
STATUS current
-- ENTERPRISE petevts 
DESCRIPTION  
"Critical Over-Voltage problem (Upper critical, going low)" 

--#TYPE       "Voltage Event" 
--#SUMMARY    "Over-Voltage Warning (Upper critical, going low)" 
--#ARGUMENTS  {} 
--#SEVERITY   CRITICAL 

::= { petevts 131336 }
 
 -- Voltage has increased above Upper critical threshold 
trapOverVoltageCriticalHigh NOTIFICATION-TYPE 
STATUS current
-- ENTERPRISE petevts 
DESCRIPTION  
"Critical Over-Voltage problem (Upper critical, going high)" 

--#TYPE       "Voltage Event" 
--#SUMMARY    "Over-Voltage Warning (Upper critical, going high)" 
--#ARGUMENTS  {} 
--#SEVERITY   CRITICAL 

::= { petevts 131337 }
 
 -- Voltage has decreased below Upper non-recoverable threshold 
trapOverVoltageNonRecoverableLow NOTIFICATION-TYPE 
STATUS current
-- ENTERPRISE petevts 
DESCRIPTION  
"Critical Over-Voltage problem (Upper non-recoverable, going low)" 

--#TYPE       "Voltage Event" 
--#SUMMARY    "Over-Voltage Warning (Upper non-recoverable, going low)" 
--#ARGUMENTS  {} 
--#SEVERITY   CRITICAL 

::= { petevts 131338 }
 
 -- Voltage has increased above Upper non-recoverable threshold 
trapOverVoltageNonRecoverableHigh NOTIFICATION-TYPE 
STATUS current
-- ENTERPRISE petevts 
DESCRIPTION  
"Critical Over-Voltage problem (Upper non-recoverable, going high)" 

--#TYPE       "Voltage Event" 
--#SUMMARY    "Under-Voltage Warning (Upper non-recoverable, going high)" 
--#ARGUMENTS  {} 
--#SEVERITY   CRITICAL 

::= { petevts 131339 }
 
-- Voltage decreased below lower non-critical threshold Cleared 
trapUnderVoltageWarningLowCleared NOTIFICATION-TYPE 
STATUS current
-- ENTERPRISE petevts 
DESCRIPTION  
"Under-Voltage Warning (Lower non-critical, going low) Cleared" 

--#TYPE       "Voltage Event" 
--#SUMMARY    "Under-Voltage Warning (Lower non-critical, going low) Cleared" 
--#ARGUMENTS  {} 
--#SEVERITY   INFORMATIONAL 

::= { petevts 131456 }
 
-- Voltage increased above lower non-critical threshold Cleared 
trapUnderVoltageWarningHighCleared NOTIFICATION-TYPE 
STATUS current
-- ENTERPRISE petevts 
DESCRIPTION  
"Under-Voltage Warning (Lower non-critical, going high)Cleared" 

--#TYPE       "Voltage Event" 
--#SUMMARY    "Under-Voltage Warning (Lower non-critical, going high)Cleared" 
--#ARGUMENTS  {} 
--#SEVERITY   INFORMATIONAL 

::= { petevts 131457 }
 
-- Voltage decreased below lower critical threshold Cleared 
trapUnderVoltageCriticalLowCleared NOTIFICATION-TYPE 
STATUS current
-- ENTERPRISE petevts 
DESCRIPTION  
"Critical Under-Voltage problem (Lower critical, going low)Cleared" 

--#TYPE       "Voltage Event" 
--#SUMMARY    "Under-Voltage Warning (Lower critical, going low)Cleared" 
--#ARGUMENTS  {} 
--#SEVERITY   INFORMATIONAL 

::= { petevts 131458 }
 
 -- Voltage increased above lower critical threshold Cleared 
trapUnderVoltageCriticalHighCleared NOTIFICATION-TYPE 
STATUS current
-- ENTERPRISE petevts 
DESCRIPTION  
"Critical Under-Voltage problem (Lower critical, going high) Cleared" 

--#TYPE       "Voltage Event" 
--#SUMMARY    "Under-Voltage Warning (Lower critical, going high) Cleared" 
--#ARGUMENTS  {} 
--#SEVERITY   INFORMATIONAL 

::= { petevts 131459 }
 
 -- Voltage decreased below lower non-recoverable threshold Cleared 
trapUnderVoltageNonRecoverableLowCleared NOTIFICATION-TYPE 
STATUS current
-- ENTERPRISE petevts 
DESCRIPTION  
"Critical Under-Voltage problem (Lower non-recoverable, going low)Cleared" 

--#TYPE       "Voltage Event" 
--#SUMMARY    "Under-Voltage Warning (Lower non-recoverable, going low)Cleared" 
--#ARGUMENTS  {} 
--#SEVERITY   INFORMATIONAL 

::= { petevts 131460 }
 
 -- Voltage increased above lower non-recoverable threshold Cleared 
trapUnderVoltageNonRecoverableHighCleared NOTIFICATION-TYPE 
STATUS current
-- ENTERPRISE petevts 
DESCRIPTION  
"Critical Under-Voltage problem (Lower non-recoverable, going high) Cleared" 

--#TYPE       "Voltage Event" 
--#SUMMARY    "Under-Voltage Warning (Lower non-recoverable, going high) Cleared" 
--#ARGUMENTS  {} 
--#SEVERITY   INFORMATIONAL 

::= { petevts 131461 }
 
-- Voltage decreased below Upper non-critical threshold Cleared 
trapOverVoltageWarningLowCleared NOTIFICATION-TYPE 
STATUS current
-- ENTERPRISE petevts 
DESCRIPTION  
"Over-Voltage Warning (Upper non-critical, going low) Cleared" 

--#TYPE       "Voltage Event" 
--#SUMMARY    "Over-Voltage Warning (Upper non-critical, going low) Cleared" 
--#ARGUMENTS  {} 
--#SEVERITY   INFORMATIONAL 

::= { petevts 131462 }
 
-- Voltage increased above upper non-critical threshold Cleared 
trapOverVoltageWarningHighCleared NOTIFICATION-TYPE 
STATUS current
-- ENTERPRISE petevts 
DESCRIPTION  
"Over-Voltage Warning (Upper non-critical, going high)Cleared" 

--#TYPE       "Voltage Event" 
--#SUMMARY    "Over-Voltage Warning (Upper non-critical, going high)Cleared" 
--#ARGUMENTS  {} 
--#SEVERITY   INFORMATIONAL 

::= { petevts 131463 }
 
-- Voltage decreased below Upper critical threshold Cleared 
trapOverVoltageCriticalLowCleared NOTIFICATION-TYPE 
STATUS current
-- ENTERPRISE petevts 
DESCRIPTION  
"Critical Over-Voltage problem (Upper critical, going low) Cleared" 

--#TYPE       "Voltage Event" 
--#SUMMARY    "Over-Voltage Warning (Upper critical, going low) Cleared" 
--#ARGUMENTS  {} 
--#SEVERITY   INFORMATIONAL 

::= { petevts 131464 }
 
 -- Voltage increased above Upper critical threshold Cleared 
trapOverVoltageCriticalHighCleared NOTIFICATION-TYPE 
STATUS current
-- ENTERPRISE petevts 
DESCRIPTION  
"Critical Over-Voltage problem (Upper critical, going high)Cleared" 

--#TYPE       "Voltage Event" 
--#SUMMARY    "Over-Voltage Warning (Upper critical, going high)Cleared" 
--#ARGUMENTS  {} 
--#SEVERITY   INFORMATIONAL 

::= { petevts 131465 }
 
 -- Voltage decreased below Upper non-recoverable threshold Cleared 
trapOverVoltageNonRecoverableLowCleared NOTIFICATION-TYPE 
STATUS current
-- ENTERPRISE petevts 
DESCRIPTION  
"Critical Over-Voltage problem (Upper non-recoverable, going low)Cleared" 

--#TYPE       "Voltage Event" 
--#SUMMARY    "Over-Voltage Warning (Upper non-recoverable, going low)Cleared" 
--#ARGUMENTS  {} 
--#SEVERITY   INFORMATIONAL 

::= { petevts 131466 }
 
 -- Voltage increased above Upper non-recoverable threshold Cleared 
trapOverVoltageNonRecoverableHighCleared NOTIFICATION-TYPE 
STATUS current
-- ENTERPRISE petevts 
DESCRIPTION  
"Critical Over-Voltage problem (Upper non-recoverable, going high) Cleared" 

--#TYPE       "Voltage Event" 
--#SUMMARY    "Under-Voltage Warning (Upper non-recoverable, going high) Cleared" 
--#ARGUMENTS  {} 
--#SEVERITY   INFORMATIONAL 

::= { petevts 131467 }
 
-- (Discrete voltage) Critical voltage problem 
trapGenericCriticalDiscreteVoltageCleared NOTIFICATION-TYPE 
STATUS current
-- ENTERPRISE petevts 
DESCRIPTION  
 "Generic Critical Voltage Problem Cleared" 

--#TYPE       "Voltage Event" 
--#SUMMARY    "Generic Critical Voltage Problem Cleared" 
--#ARGUMENTS  {} 
--#SEVERITY   INFORMATIONAL 

::= { petevts 131840 }

-- (Discrete voltage) Critical voltage problem 
trapGenericCriticalDiscreteVoltage NOTIFICATION-TYPE 
STATUS current
-- ENTERPRISE petevts 
DESCRIPTION  
 "Generic Critical Voltage Problem (Transition to Critical from less severe)" 

--#TYPE       "Voltage Event" 
--#SUMMARY    "Generic Critical Voltage Problem (Transition to Critical from less severe)" 
--#ARGUMENTS  {} 
--#SEVERITY   CRITICAL 

::= { petevts 131841 }
 
-- (Discrete voltage) Critical voltage problem cleared 
trapGenericCriticalDiscreteVoltage2Cleared NOTIFICATION-TYPE 
STATUS current
-- ENTERPRISE petevts 
DESCRIPTION  
 "Generic Critical Voltage Problem Cleared(Transition to OK)" 

--#TYPE	      "Voltage Event" 
--#SUMMARY    "Generic Critical Voltage Problem Cleared(Transition to OK)" 
--#ARGUMENTS  {} 
--#SEVERITY   INFORMATIONAL 

::= { petevts 132864 }
 
-- (Discrete voltage) Non-Critical voltage problem  
trapGenericNonCriticalDiscreteVoltage2 NOTIFICATION-TYPE 
STATUS current
-- ENTERPRISE petevts 
DESCRIPTION  
 "Generic Non-Critical Voltage Problem (Transition to Non-critical from OK)" 

--#TYPE	      "Voltage Event" 
--#SUMMARY    "Generic Critical Voltage Problem (Transition to Non-critical from OK)" 
--#ARGUMENTS  {} 
--#SEVERITY   WARNING 

::= { petevts 132865 }
 
-- (Discrete voltage) Critical voltage problem 
trapGenericCriticalDiscreteVoltage2 NOTIFICATION-TYPE 
STATUS current
-- ENTERPRISE petevts 
DESCRIPTION  
 "Generic Critical Voltage Problem (Transition to Critical from less severe)" 

--#TYPE	      "Voltage Event" 
--#SUMMARY    "Generic Critical Voltage Problem (Transition to Critical from less severe)" 
--#ARGUMENTS  {} 
--#SEVERITY   CRITICAL 

::= { petevts 132866 }

-- (Discrete voltage) Non-Critical voltage problem 
trapGenericDiscreteVoltageWarning NOTIFICATION-TYPE 
STATUS current
-- ENTERPRISE petevts 
DESCRIPTION  
 "Generic Voltage Warning (Transition to Non-Critical from less severe)" 

--#TYPE	      "Voltage Event" 
--#SUMMARY    "Generic Voltage Warning (Transition to Non-Critical from less severe)" 
--#ARGUMENTS  {} 
--#SEVERITY   WARNING 

::= { petevts 132867 }

-- (Discrete voltage) Non-Critical voltage problem 
trapGenericDiscreteVoltageWarning2 NOTIFICATION-TYPE 
STATUS current
-- ENTERPRISE petevts 
DESCRIPTION  
 "Generic Voltage Warning (Transition to Non-Critical from more severe)" 

--#TYPE	      "Voltage Event" 
--#SUMMARY    "Generic Voltage Warning (Transition to Non-Critical from more severe)" 
--#ARGUMENTS  {} 
--#SEVERITY   WARNING 

::= { petevts 132868 }
 
-- (Discrete voltage) Non-Recoverable voltage problem 
trapGenericDiscreteVoltageNonRecoverable NOTIFICATION-TYPE 
STATUS current
-- ENTERPRISE petevts 
DESCRIPTION  
 "Generic Voltage Warning (Transition to Non-Recoverable)" 

--#TYPE	      "Voltage Event" 
--#SUMMARY    "Generic Voltage Warning (Transition to Non-Recoverable)" 
--#ARGUMENTS  {} 
--#SEVERITY   CRITICAL 

::= { petevts 132869 }
 
 -- (Discrete voltage) Non-Recoverable voltage problem 
trapGenericDiscreteVoltageMonitor NOTIFICATION-TYPE 
STATUS current
-- ENTERPRISE petevts 
DESCRIPTION  
 "Generic Discrete Voltage  (Monitor)" 

--#TYPE	      "Voltage Event" 
--#SUMMARY    "Generic Discrete Voltage (Monitor)" 
--#ARGUMENTS  {} 
--#SEVERITY   INFORMATIONAL 

::= { petevts 132870 }
 
  -- (Discrete voltage) Non-Recoverable voltage problem 
trapGenericDiscreteVoltageInformational NOTIFICATION-TYPE 
STATUS current
-- ENTERPRISE petevts 
DESCRIPTION  
 "Generic Discrete Voltage  (Informational)" 

--#TYPE	      "Voltage Event" 
--#SUMMARY    "Generic Discrete Voltage (Informational)" 
--#ARGUMENTS  {} 
--#SEVERITY   INFORMATIONAL 

::= { petevts 132871 }
 
-- ********************************************** 
-- *		Current			* 
-- ********************************************** 

-- Current has decreased below lower non-critical threshold 
trapUnderCurrentWarningLow NOTIFICATION-TYPE 
STATUS current
-- ENTERPRISE petevts 
DESCRIPTION  
"Under-Current Warning (Lower non-critical, going low)" 

--#TYPE       "Current Event" 
--#SUMMARY    "Under-Current Warning (Lower non-critical, going low)" 
--#ARGUMENTS  {} 
--#SEVERITY   WARNING 

::= { petevts 196864 }
 
-- Current has increased above lower non-critical threshold 
trapUnderCurrentWarningHigh NOTIFICATION-TYPE 
STATUS current
-- ENTERPRISE petevts 
DESCRIPTION  
"Under-Current Warning (Lower non-critical, going high)" 

--#TYPE       "Current Event" 
--#SUMMARY    "Under-Current Warning (Lower non-critical, going high)" 
--#ARGUMENTS  {} 
--#SEVERITY   WARNING 

::= { petevts 196865 }
 
-- Current has decreased below lower critical threshold 
trapUnderCurrentCriticalLow NOTIFICATION-TYPE 
STATUS current
-- ENTERPRISE petevts 
DESCRIPTION  
"Critical Under-Current problem (Lower critical, going low)" 

--#TYPE       "Current Event" 
--#SUMMARY    "Under-Current Warning (Lower critical, going low)" 
--#ARGUMENTS  {} 
--#SEVERITY   CRITICAL 

::= { petevts 196866 }
 
 -- Current has increased above lower critical threshold 
trapUnderCurrentCriticalHigh NOTIFICATION-TYPE 
STATUS current
-- ENTERPRISE petevts 
DESCRIPTION  
"Critical Under-Current problem (Lower critical, going high)" 

--#TYPE       "Current Event" 
--#SUMMARY    "Under-Current Warning (Lower critical, going high)" 
--#ARGUMENTS  {} 
--#SEVERITY   CRITICAL 

::= { petevts 196867 }
 
 -- Current has decreased below lower non-recoverable threshold 
trapUnderCurrentNonRecoverableLow NOTIFICATION-TYPE 
STATUS current
-- ENTERPRISE petevts 
DESCRIPTION  
"Critical Under-Current problem (Lower non-recoverable, going low)" 

--#TYPE       "Current Event" 
--#SUMMARY    "Under-Current Warning (Lower non-recoverable, going low)" 
--#ARGUMENTS  {} 
--#SEVERITY   CRITICAL 

::= { petevts 196868 }
 
 -- Current has increased above lower non-recoverable threshold 
trapUnderCurrentNonRecoverableHigh NOTIFICATION-TYPE 
STATUS current
-- ENTERPRISE petevts 
DESCRIPTION  
"Critical Under-Current problem (Lower non-recoverable, going high)" 

--#TYPE       "Current Event" 
--#SUMMARY    "Under-Current Warning (Lower non-recoverable, going high)" 
--#ARGUMENTS  {} 
--#SEVERITY   CRITICAL 

::= { petevts 196869 }
 
-- Current has decreased below Upper non-critical threshold 
trapOverCurrentWarningLow NOTIFICATION-TYPE 
STATUS current
-- ENTERPRISE petevts 
DESCRIPTION  
"Over-Current Warning (Upper non-critical, going low)" 

--#TYPE       "Current Event" 
--#SUMMARY    "Over-Current Warning (Upper non-critical, going low)" 
--#ARGUMENTS  {} 
--#SEVERITY   WARNING 

::= { petevts 196870 }
 
-- Current has increased above upper non-critical threshold. 
trapOverCurrentWarningHigh NOTIFICATION-TYPE 
STATUS current
-- ENTERPRISE petevts 
DESCRIPTION  
"Over-Current Warning (Upper non-critical, going high)" 

--#TYPE       "Current Event" 
--#SUMMARY    "Over-Current Warning (Upper non-critical, going high)" 
--#ARGUMENTS  {} 
--#SEVERITY   WARNING 

::= { petevts 196871 }
 
-- Current has decreased below Upper critical threshold 
trapOverCurrentCriticalLow NOTIFICATION-TYPE 
STATUS current
-- ENTERPRISE petevts 
DESCRIPTION  
"Critical Over-Current problem (Upper critical, going low)" 

--#TYPE       "Current Event" 
--#SUMMARY    "Over-Current Warning (Upper critical, going low)" 
--#ARGUMENTS  {} 
--#SEVERITY   CRITICAL 

::= { petevts 196872 }
 
 -- Current has increased above Upper critical threshold 
trapOverCurrentCriticalHigh NOTIFICATION-TYPE 
STATUS current
-- ENTERPRISE petevts 
DESCRIPTION  
"Critical Over-Current problem (Upper critical, going high)" 

--#TYPE       "Current Event" 
--#SUMMARY    "Over-Current Warning (Upper critical, going high)" 
--#ARGUMENTS  {} 
--#SEVERITY   CRITICAL 

::= { petevts 196873 }
 
 -- Current has decreased below Upper non-recoverable threshold 
trapOverCurrentNonRecoverableLow NOTIFICATION-TYPE 
STATUS current
-- ENTERPRISE petevts 
DESCRIPTION  
"Critical Over-Current problem (Upper non-recoverable, going low)" 

--#TYPE       "Current Event" 
--#SUMMARY    "Over-Current Warning (Upper non-recoverable, going low)" 
--#ARGUMENTS  {} 
--#SEVERITY   CRITICAL 

::= { petevts 196874 }
 
 -- Current has increased above Upper non-recoverable threshold 
trapOverCurrentNonRecoverableHigh NOTIFICATION-TYPE 
STATUS current
-- ENTERPRISE petevts 
DESCRIPTION  
"Critical Over-Current problem (Upper non-recoverable, going high)" 

--#TYPE       "Current Event" 
--#SUMMARY    "Under-Current Warning (Upper non-recoverable, going high)" 
--#ARGUMENTS  {} 
--#SEVERITY   CRITICAL 

::= { petevts 196875 }
 
-- Current decreased below lower non-critical threshold Cleared 
trapUnderCurrentWarningLowCleared NOTIFICATION-TYPE 
STATUS current
-- ENTERPRISE petevts 
DESCRIPTION  
"Under-Current Warning (Lower non-critical, going low) Cleared" 

--#TYPE       "Current Event" 
--#SUMMARY    "Under-Current Warning (Lower non-critical, going low) Cleared" 
--#ARGUMENTS  {} 
--#SEVERITY   INFORMATIONAL 

::= { petevts 196992 }
 
-- Current increased above lower non-critical threshold Cleared 
trapUnderCurrentWarningHighCleared NOTIFICATION-TYPE 
STATUS current
-- ENTERPRISE petevts 
DESCRIPTION  
"Under-Current Warning (Lower non-critical, going high)Cleared" 

--#TYPE       "Current Event" 
--#SUMMARY    "Under-Current Warning (Lower non-critical, going high)Cleared" 
--#ARGUMENTS  {} 
--#SEVERITY   INFORMATIONAL 

::= { petevts 196993 }
 
-- Current decreased below lower critical threshold Cleared 
trapUnderCurrentCriticalLowCleared NOTIFICATION-TYPE 
STATUS current
-- ENTERPRISE petevts 
DESCRIPTION  
"Critical Under-Current problem (Lower critical, going low)Cleared" 

--#TYPE       "Current Event" 
--#SUMMARY    "Under-Current Warning (Lower critical, going low)Cleared" 
--#ARGUMENTS  {} 
--#SEVERITY   INFORMATIONAL 

::= { petevts 196994 }
 
 -- Current increased above lower critical threshold Cleared 
trapUnderCurrentCriticalHighCleared NOTIFICATION-TYPE 
STATUS current
-- ENTERPRISE petevts 
DESCRIPTION  
"Critical Under-Current problem (Lower critical, going high) Cleared" 

--#TYPE       "Current Event" 
--#SUMMARY    "Under-Current Warning (Lower critical, going high) Cleared" 
--#ARGUMENTS  {} 
--#SEVERITY   INFORMATIONAL 

::= { petevts 196995 }
 
 -- Current decreased below lower non-recoverable threshold Cleared 
trapUnderCurrentNonRecoverableLowCleared NOTIFICATION-TYPE 
STATUS current
-- ENTERPRISE petevts 
DESCRIPTION  
"Critical Under-Current problem (Lower non-recoverable, going low)Cleared" 

--#TYPE       "Current Event" 
--#SUMMARY    "Under-Current Warning (Lower non-recoverable, going low)Cleared" 
--#ARGUMENTS  {} 
--#SEVERITY   INFORMATIONAL 

::= { petevts 196996 }
 
 -- Current increased above lower non-recoverable threshold Cleared 
trapUnderCurrentNonRecoverableHighCleared NOTIFICATION-TYPE 
STATUS current
-- ENTERPRISE petevts 
DESCRIPTION  
"Critical Under-Current problem (Lower non-recoverable, going high) Cleared" 

--#TYPE       "Current Event" 
--#SUMMARY    "Under-Current Warning (Lower non-recoverable, going high) Cleared" 
--#ARGUMENTS  {} 
--#SEVERITY   INFORMATIONAL 

::= { petevts 196997 }
 
-- Current decreased below Upper non-critical threshold Cleared 
trapOverCurrentWarningLowCleared NOTIFICATION-TYPE 
STATUS current
-- ENTERPRISE petevts 
DESCRIPTION  
"Over-Current Warning (Upper non-critical, going low) Cleared" 

--#TYPE       "Current Event" 
--#SUMMARY    "Over-Current Warning (Upper non-critical, going low) Cleared" 
--#ARGUMENTS  {} 
--#SEVERITY   INFORMATIONAL 

::= { petevts 196998 }
 
-- Current increased above upper non-critical threshold Cleared 
trapOverCurrentWarningHighCleared NOTIFICATION-TYPE 
STATUS current
-- ENTERPRISE petevts 
DESCRIPTION  
"Over-Current Warning (Upper non-critical, going high)Cleared" 

--#TYPE       "Current Event" 
--#SUMMARY    "Over-Current Warning (Upper non-critical, going high)Cleared" 
--#ARGUMENTS  {} 
--#SEVERITY   INFORMATIONAL 

::= { petevts 196999 }
 
-- Current decreased below Upper critical threshold Cleared 
trapOverCurrentCriticalLowCleared NOTIFICATION-TYPE 
STATUS current
-- ENTERPRISE petevts 
DESCRIPTION  
"Critical Over-Current problem (Upper critical, going low) Cleared" 

--#TYPE       "Current Event" 
--#SUMMARY    "Over-Current Warning (Upper critical, going low) Cleared" 
--#ARGUMENTS  {} 
--#SEVERITY   INFORMATIONAL 

::= { petevts 197000 }
 
 -- Current increased above Upper critical threshold Cleared 
trapOverCurrentCriticalHighCleared NOTIFICATION-TYPE 
STATUS current
-- ENTERPRISE petevts 
DESCRIPTION  
"Critical Over-Current problem (Upper critical, going high)Cleared" 

--#TYPE       "Current Event" 
--#SUMMARY    "Over-Current Warning (Upper critical, going high)Cleared" 
--#ARGUMENTS  {} 
--#SEVERITY   INFORMATIONAL 

::= { petevts 197001 }
 
 -- Current decreased below Upper non-recoverable threshold Cleared 
trapOverCurrentNonRecoverableLowCleared NOTIFICATION-TYPE 
STATUS current
-- ENTERPRISE petevts 
DESCRIPTION  
"Critical Over-Current problem (Upper non-recoverable, going low)Cleared" 

--#TYPE       "Current Event" 
--#SUMMARY    "Over-Current Warning (Upper non-recoverable, going low)Cleared" 
--#ARGUMENTS  {} 
--#SEVERITY   INFORMATIONAL 

::= { petevts 197002 }
 
 -- Current increased above Upper non-recoverable threshold Cleared 
trapOverCurrentNonRecoverableHighCleared NOTIFICATION-TYPE 
STATUS current
-- ENTERPRISE petevts 
DESCRIPTION  
"Critical Over-Current problem (Upper non-recoverable, going high) Cleared" 

--#TYPE       "Current Event" 
--#SUMMARY    "Under-Current Warning (Upper non-recoverable, going high) Cleared" 
--#ARGUMENTS  {} 
--#SEVERITY   INFORMATIONAL 

::= { petevts 197003 }
 
 
-- ********************************************** 
-- *		Fan			* 
-- ********************************************** 

-- Fan speed has decreased below lower non-critical threshold 
trapFanUnderSpeedWarningLow NOTIFICATION-TYPE 
STATUS current
-- ENTERPRISE petevts 
DESCRIPTION  
"Fan Under Speed Warning (Lower non-critical, going low)" 

--#TYPE       "Fan Event" 
--#SUMMARY    "Fan Under Speed Warning (Lower non-critical, going low)" 
--#ARGUMENTS  {} 
--#SEVERITY   WARNING 

::= { petevts 262400 }
 
-- Fan speed has increased above lower non-critical threshold 
trapFanUnderSpeedWarningHigh NOTIFICATION-TYPE 
STATUS current
-- ENTERPRISE petevts 
DESCRIPTION  
"Fan Under Speed Warning (Lower non-critical, going high)" 

--#TYPE       "Fan Event" 
--#SUMMARY    "Fan Under Speed Warning (Lower non-critical, going high)" 
--#ARGUMENTS  {} 
--#SEVERITY   WARNING 

::= { petevts 262401 }
 
-- Fan speed has decreased below lower critical threshold 
trapFanUnderSpeedCriticalLow NOTIFICATION-TYPE 
STATUS current
-- ENTERPRISE petevts 
DESCRIPTION  
"Critical Fan Under Speed problem (Lower critical, going low)" 

--#TYPE       "Fan Event" 
--#SUMMARY    "Fan Under Speed Warning (Lower critical, going low)" 
--#ARGUMENTS  {} 
--#SEVERITY   CRITICAL 

::= { petevts 262402 }
 
 -- Fan speed has increased above lower critical threshold 
trapFanUnderSpeedCriticalHigh NOTIFICATION-TYPE 
STATUS current
-- ENTERPRISE petevts 
DESCRIPTION  
"Critical Fan Under Speed problem (Lower critical, going high)" 

--#TYPE       "Fan Event" 
--#SUMMARY    "Fan Under Speed Warning (Lower critical, going high)" 
--#ARGUMENTS  {} 
--#SEVERITY   CRITICAL 

::= { petevts 262403 }
 
 -- Fan speed has decreased below lower non-recoverable threshold 
trapFanUnderSpeedNonRecoverableLow NOTIFICATION-TYPE 
STATUS current
-- ENTERPRISE petevts 
DESCRIPTION  
"Critical Fan Under Speed problem (Lower non-recoverable, going low)" 

--#TYPE       "Fan Event" 
--#SUMMARY    "Fan Under Speed Warning (Lower non-recoverable, going low)" 
--#ARGUMENTS  {} 
--#SEVERITY   CRITICAL 

::= { petevts 262404 }
 
 -- Fan speed has increased above lower non-recoverable threshold 
trapFanUnderSpeedNonRecoverableHigh NOTIFICATION-TYPE 
STATUS current
-- ENTERPRISE petevts 
DESCRIPTION  
"Critical Fan Under Speed problem (Lower non-recoverable, going high)" 

--#TYPE       "Fan Event" 
--#SUMMARY    "Fan Under Speed Warning (Lower non-recoverable, going high)" 
--#ARGUMENTS  {} 
--#SEVERITY   CRITICAL 

::= { petevts 262405 }
 
-- Fan speed has decreased below Upper non-critical threshold 
trapFanOverSpeedWarningLow NOTIFICATION-TYPE 
STATUS current
-- ENTERPRISE petevts 
DESCRIPTION  
"Fan Over Speed Warning (Upper non-critical, going low)" 

--#TYPE       "Fan Event" 
--#SUMMARY    "Fan Over Speed Warning (Upper non-critical, going low)" 
--#ARGUMENTS  {} 
--#SEVERITY   WARNING 

::= { petevts 262406 }
 
-- Fan speed has increased above upper non-critical threshold. 
trapFanOverSpeedWarningHigh NOTIFICATION-TYPE 
STATUS current
-- ENTERPRISE petevts 
DESCRIPTION  
"Fan Over Speed Warning (Upper non-critical, going high)" 

--#TYPE       "Fan Event" 
--#SUMMARY    "Fan Over Speed Warning (Upper non-critical, going high)" 
--#ARGUMENTS  {} 
--#SEVERITY   WARNING 

::= { petevts 262407 }
 
-- Fan speed has decreased below Upper critical threshold 
trapFanOverSpeedCriticalLow NOTIFICATION-TYPE 
STATUS current
-- ENTERPRISE petevts 
DESCRIPTION  
"Critical Fan Over Speed problem (Upper critical, going low)" 

--#TYPE       "Fan Event" 
--#SUMMARY    "Fan Over Speed Warning (Upper critical, going low)" 
--#ARGUMENTS  {} 
--#SEVERITY   CRITICAL 

::= { petevts 262408 }
 
 -- Fan speed has increased above Upper critical threshold 
trapFanOverSpeedCriticalHigh NOTIFICATION-TYPE 
STATUS current
-- ENTERPRISE petevts 
DESCRIPTION  
"Critical Fan Over Speed problem (Upper critical, going high)" 

--#TYPE       "Fan Event" 
--#SUMMARY    "Fan Over Speed Warning (Upper critical, going high)" 
--#ARGUMENTS  {} 
--#SEVERITY   CRITICAL 

::= { petevts 262409 }
 
 -- Fan speed has decreased below Upper non-recoverable threshold 
trapFanOverSpeedNonRecoverableLow NOTIFICATION-TYPE 
STATUS current
-- ENTERPRISE petevts 
DESCRIPTION  
"Critical Fan Over Speed problem (Upper non-recoverable, going low)" 

--#TYPE       "Fan Event" 
--#SUMMARY    "Fan Over Speed Warning (Upper non-recoverable, going low)" 
--#ARGUMENTS  {} 
--#SEVERITY   CRITICAL 

::= { petevts 262410 }
 
 -- Fan speed has increased above Upper non-recoverable threshold 
trapFanOverSpeedNonRecoverableHigh NOTIFICATION-TYPE 
STATUS current
-- ENTERPRISE petevts 
DESCRIPTION  
"Critical Fan Over Speed problem (Upper non-recoverable, going high)" 

--#TYPE       "Fan Event" 
--#SUMMARY    "Fan Under Speed Warning (Upper non-recoverable, going high)" 
--#ARGUMENTS  {} 
--#SEVERITY   CRITICAL 

::= { petevts 262411 }
 
-- Fan speed has increased above Upper non-recoverable threshold 
trapWxlTest NOTIFICATION-TYPE 
STATUS current
-- ENTERPRISE petevts 
DESCRIPTION  
"test" 

--#TYPE       "Fan Event" 
--#SUMMARY    "Fan Under Speed Warning (Upper non-recoverable, going high)" 
--#ARGUMENTS  {} 
--#SEVERITY   CRITICAL 

::= { petevts 262412 }
 
-- Fan speed decreased below lower non-critical threshold Cleared 
trapFanUnderSpeedWarningLowCleared NOTIFICATION-TYPE 
STATUS current
-- ENTERPRISE petevts 
DESCRIPTION  
"Fan Under Speed Warning (Lower non-critical, going low) Cleared" 

--#TYPE       "Fan Event" 
--#SUMMARY    "Fan Under Speed Warning (Lower non-critical, going low) Cleared" 
--#ARGUMENTS  {} 
--#SEVERITY   INFORMATIONAL 

::= { petevts 262528 }
 
-- Fan speed increased above lower non-critical threshold Cleared 
trapFanUnderSpeedWarningHighCleared NOTIFICATION-TYPE 
STATUS current
-- ENTERPRISE petevts 
DESCRIPTION  
"Fan Under Speed Warning (Lower non-critical, going high)Cleared" 

--#TYPE       "Fan Event" 
--#SUMMARY    "Fan Under Speed Warning (Lower non-critical, going high)Cleared" 
--#ARGUMENTS  {} 
--#SEVERITY   INFORMATIONAL 

::= { petevts 262529 }
 
-- Fan speed decreased below lower critical threshold Cleared 
trapFanUnderSpeedCriticalLowCleared NOTIFICATION-TYPE 
STATUS current
-- ENTERPRISE petevts 
DESCRIPTION  
"Critical Fan Under Speed problem (Lower critical, going low)Cleared" 

--#TYPE       "Fan Event" 
--#SUMMARY    "Fan Under Speed Warning (Lower critical, going low)Cleared" 
--#ARGUMENTS  {} 
--#SEVERITY   INFORMATIONAL 

::= { petevts 262530 }
 
 -- Fan speed increased above lower critical threshold Cleared 
trapFanUnderSpeedCriticalHighCleared NOTIFICATION-TYPE 
STATUS current
-- ENTERPRISE petevts 
DESCRIPTION  
"Critical Fan Under Speed problem (Lower critical, going high) Cleared" 

--#TYPE       "Fan Event" 
--#SUMMARY    "Fan Under Speed Warning (Lower critical, going high) Cleared" 
--#ARGUMENTS  {} 
--#SEVERITY   INFORMATIONAL 

::= { petevts 262531 }
 
 -- Fan speed decreased below lower non-recoverable threshold Cleared 
trapFanUnderSpeedNonRecoverableLowCleared NOTIFICATION-TYPE 
STATUS current
-- ENTERPRISE petevts 
DESCRIPTION  
"Critical Fan Under Speed problem (Lower non-recoverable, going low)Cleared" 

--#TYPE       "Fan Event" 
--#SUMMARY    "Fan Under Speed Warning (Lower non-recoverable, going low)Cleared" 
--#ARGUMENTS  {} 
--#SEVERITY   INFORMATIONAL 

::= { petevts 262532 }
 
 -- Fan speed increased above lower non-recoverable threshold Cleared 
trapFanUnderSpeedNonRecoverableHighCleared NOTIFICATION-TYPE 
STATUS current
-- ENTERPRISE petevts 
DESCRIPTION  
"Critical Fan Under Speed problem (Lower non-recoverable, going high) Cleared" 

--#TYPE       "Fan Event" 
--#SUMMARY    "Fan Under Speed Warning (Lower non-recoverable, going high) Cleared" 
--#ARGUMENTS  {} 
--#SEVERITY   INFORMATIONAL 

::= { petevts 262533 }
 
-- Fan speed decreased below Upper non-critical threshold Cleared 
trapFanOverSpeedWarningLowCleared NOTIFICATION-TYPE 
STATUS current
-- ENTERPRISE petevts 
DESCRIPTION  
"Fan Over Speed Warning (Upper non-critical, going low) Cleared" 

--#TYPE       "Fan Event" 
--#SUMMARY    "Fan Over Speed Warning (Upper non-critical, going low) Cleared" 
--#ARGUMENTS  {} 
--#SEVERITY   INFORMATIONAL 

::= { petevts 262534 }
 
-- Fan speed increased above upper non-critical threshold Cleared 
trapFanOverSpeedWarningHighCleared NOTIFICATION-TYPE 
STATUS current
-- ENTERPRISE petevts 
DESCRIPTION  
"Fan Over Speed Warning (Upper non-critical, going high)Cleared" 

--#TYPE       "Fan Event" 
--#SUMMARY    "Fan Over Speed Warning (Upper non-critical, going high)Cleared" 
--#ARGUMENTS  {} 
--#SEVERITY   INFORMATIONAL 

::= { petevts 262535 }
 
-- Fan speed decreased below Upper critical threshold Cleared 
trapFanOverSpeedCriticalLowCleared NOTIFICATION-TYPE 
STATUS current
-- ENTERPRISE petevts 
DESCRIPTION  
"Critical Fan Over Speed problem (Upper critical, going low) Cleared" 

--#TYPE       "Fan Event" 
--#SUMMARY    "Fan Over Speed Warning (Upper critical, going low) Cleared" 
--#ARGUMENTS  {} 
--#SEVERITY   INFORMATIONAL 

::= { petevts 262536 }
 
 -- Fan speed increased above Upper critical threshold Cleared 
trapFanOverSpeedCriticalHighCleared NOTIFICATION-TYPE 
STATUS current
-- ENTERPRISE petevts 
DESCRIPTION  
"Critical Fan Over Speed problem (Upper critical, going high)Cleared" 

--#TYPE       "Fan Event" 
--#SUMMARY    "Fan Over Speed Warning (Upper critical, going high)Cleared" 
--#ARGUMENTS  {} 
--#SEVERITY   INFORMATIONAL 

::= { petevts 262537 }
 
 -- Fan speed decreased below Upper non-recoverable threshold Cleared 
trapFanOverSpeedNonRecoverableLowCleared NOTIFICATION-TYPE 
STATUS current
-- ENTERPRISE petevts 
DESCRIPTION  
"Critical Fan Over Speed problem (Upper non-recoverable, going low)Cleared" 

--#TYPE       "Fan Event" 
--#SUMMARY    "Fan Over Speed Warning (Upper non-recoverable, going low)Cleared" 
--#ARGUMENTS  {} 
--#SEVERITY   INFORMATIONAL 

::= { petevts 262538 }
 
 -- Fan speed increased above Upper non-recoverable threshold Cleared 
trapFanOverSpeedNonRecoverableHighCleared NOTIFICATION-TYPE 
STATUS current
-- ENTERPRISE petevts 
DESCRIPTION  
"Critical Fan Over Speed problem (Upper non-recoverable, going high) Cleared" 

--#TYPE       "Fan Event" 
--#SUMMARY    "Fan Under Speed Warning (Upper non-recoverable, going high) Cleared" 
--#ARGUMENTS  {} 
--#SEVERITY   INFORMATIONAL 

::= { petevts 262539 }
 
 -- Fan Removed/Absent 
trapFanRemoved NOTIFICATION-TYPE 
STATUS current
-- ENTERPRISE petevts 
DESCRIPTION  
 "Fan Removed/Absent" 

--#TYPE       "Fan Event" 
--#SUMMARY    "Fan Removed/Absent" 
--#ARGUMENTS  {} 
--#SEVERITY   CRITICAL 

::= { petevts 264192 }
 
  -- Fan Inserted/Present 
trapFanInserted NOTIFICATION-TYPE 
STATUS current
-- ENTERPRISE petevts 
DESCRIPTION  
 "Fan Inserted/Present" 

--#TYPE       "Fan Event" 
--#SUMMARY    "Fan Inserted/Present" 
--#ARGUMENTS  {} 
--#SEVERITY   INFORMATIONAL 

::= { petevts 264193 }
 
-- Fan Full Redundancy  
trapFanFullRedundancy NOTIFICATION-TYPE 
STATUS current
-- ENTERPRISE petevts 
DESCRIPTION  
 "Fan redundancy has returned to Normal" 

--#TYPE       "Fan Event" 
--#SUMMARY    "Fan redundancy has returned to Normal" 
--#ARGUMENTS  {} 
--#SEVERITY   INFORMATIONAL 

::= { petevts 264960 }

-- Fan Redundancy lost  
trapFanRedundancyLost NOTIFICATION-TYPE 
STATUS current
-- ENTERPRISE petevts 
DESCRIPTION  
 "Fan Redundancy has been Lost" 

--#TYPE       "Fan Event" 
--#SUMMARY    "Fan Redundancy has been Lost" 
--#ARGUMENTS  {} 
--#SEVERITY   CRITICAL 

::= { petevts 264961 }

-- Fan Redundancy degraded 
trapFanRedundancyDegraded NOTIFICATION-TYPE 
STATUS current
-- ENTERPRISE petevts 
DESCRIPTION  
 "Fan Redundancy is in a degraded state" 

--#TYPE       "Fan Event" 
--#SUMMARY    "Fan Redundancy is in a degraded state" 
--#ARGUMENTS  {} 
--#SEVERITY   WARNING 

::= { petevts 264962 }
 
--********************** 
--* Chassis Intrusion  * 
--********************** }

--Chassis Intrusion 
trapChassisIntrusion NOTIFICATION-TYPE 
STATUS current
-- ENTERPRISE petevts 
DESCRIPTION  
 "Chassis Intrusion - Physical Security Violation" 

--#TYPE       "Chassis Intrusion Event" 
--#SUMMARY    "Chassis Intrusion - Physical Security Violation" 
--#ARGUMENTS  {} 
--#SEVERITY   CRITICAL 

::= { petevts 356096 }

--Chassis Drive Bay Intrusion 
trapChassisDriveBayIntrusion NOTIFICATION-TYPE 
STATUS current
-- ENTERPRISE petevts 
DESCRIPTION  
 "Chassis Intrusion - Drive Bay Violation" 

--#TYPE       "Chassis Intrusion Event" 
--#SUMMARY    "Chassis Intrusion - Drive Bay Violation" 
--#ARGUMENTS  {} 
--#SEVERITY   CRITICAL 

::= { petevts 356097 }
 
 -- I/O Card Area Intrusion 
trapChassisIOCardAreaIntrusion NOTIFICATION-TYPE 
STATUS current
-- ENTERPRISE petevts 
DESCRIPTION  
 "I/O Card Area Intrusion" 

--#TYPE       "Chassis Intrusion Event" 
--#SUMMARY    "I/O Card Area Intrusion" 
--#ARGUMENTS  {} 
--#SEVERITY   CRITICAL 

::= { petevts 356098 }
 
  -- Processor Area Intrusion 
trapChassisProcessorAreaIntrusion NOTIFICATION-TYPE 
STATUS current
-- ENTERPRISE petevts 
DESCRIPTION  
 "Processor Area Intrusion" 

--#TYPE       "Chassis Intrusion Event" 
--#SUMMARY    "Processor Area Intrusion" 
--#ARGUMENTS  {} 
--#SEVERITY   CRITICAL 

::= { petevts 356099 }
 
   -- LAN Leash Lost 
trapChassisLANLeashLost NOTIFICATION-TYPE 
STATUS current
-- ENTERPRISE petevts 
DESCRIPTION  
 "LAN Leash Lost" 

--#TYPE       "Chassis Intrusion Event" 
--#SUMMARY    "LAN Leash Lost" 
--#ARGUMENTS  {} 
--#SEVERITY   CRITICAL 

::= { petevts 356100 }
 
    -- Unauthorized dock 
trapChassisUnauthorizedDock NOTIFICATION-TYPE 
STATUS current
-- ENTERPRISE petevts 
DESCRIPTION  
 "Unauthorized dock" 

--#TYPE       "Chassis Intrusion Event" 
--#SUMMARY    "Unauthorized dock" 
--#ARGUMENTS  {} 
--#SEVERITY   CRITICAL 

::= { petevts 356101 }
 
     -- Fan Area Intrusion 
trapChassisFanAreaIntrusion NOTIFICATION-TYPE 
STATUS current
-- ENTERPRISE petevts 
DESCRIPTION  
 "Fan Area Intrusion" 

--#TYPE       "Chassis Intrusion Event" 
--#SUMMARY    "Fan Area Intrusion" 
--#ARGUMENTS  {} 
--#SEVERITY   CRITICAL 

::= { petevts 356102 }
 
-- Chassis Intrusion cleared 
trapChassisIntrusionCleared NOTIFICATION-TYPE 
STATUS current
-- ENTERPRISE petevts 
DESCRIPTION  
"Chassis Intrusion (Physical Security Violation) Event Cleared" 

--#TYPE       "Chassis Intrusion Event" 
--#SUMMARY    "Chassis Intrusion( Physical Security Violation) Event Cleared" 
--#ARGUMENTS  {} 
--#SEVERITY   INFORMATIONAL 

::= { petevts 356224 }

 -- Chassis Drive Bay Intrusion Cleared 
trapChassisDriveBayIntrusionCleared NOTIFICATION-TYPE 
STATUS current
-- ENTERPRISE petevts 
DESCRIPTION  
 "Chassis Intrusion - Drive Bay Violation Cleared" 

--#TYPE       "Chassis Intrusion Event" 
--#SUMMARY    "Chassis Intrusion - Drive Bay Violation Cleared" 
--#ARGUMENTS  {} 
--#SEVERITY   INFORMATIONAL 

::= { petevts 356225 }
 
  -- I/O Card Area Intrusion Cleared 
trapChassisIOCardAreaIntrusionCleared NOTIFICATION-TYPE 
STATUS current
-- ENTERPRISE petevts 
DESCRIPTION  
 "I/O Card Area Intrusion Cleared" 

--#TYPE       "Chassis Intrusion Event" 
--#SUMMARY    "I/O Card Area Intrusion Cleared" 
--#ARGUMENTS  {} 
--#SEVERITY   INFORMATIONAL 

::= { petevts 356226 }
 
  -- Processor Area Intrusion Cleared 
trapChassisProcessorAreaIntrusionCleared NOTIFICATION-TYPE 
STATUS current
-- ENTERPRISE petevts 
DESCRIPTION  
 "Processor Area Intrusion Cleared" 

--#TYPE       "Chassis Intrusion Event" 
--#SUMMARY    "Processor Area Intrusion Cleared" 
--#ARGUMENTS  {} 
--#SEVERITY   INFORMATIONAL 

::= { petevts 356227 }
 
   -- LAN Leash Lost Cleared 
trapChassisLANLeashLostCleared NOTIFICATION-TYPE 
STATUS current
-- ENTERPRISE petevts 
DESCRIPTION  
 "LAN Leash Lost" 

--#TYPE       "Chassis Intrusion Event" 
--#SUMMARY    "LAN Leash Lost Cleared" 
--#ARGUMENTS  {} 
--#SEVERITY   INFORMATIONAL 

::= { petevts 356228 }
 
    -- Unauthorized dock Cleared 
trapChassisUnauthorizedDockCleared NOTIFICATION-TYPE 
STATUS current
-- ENTERPRISE petevts 
DESCRIPTION  
 "Unauthorized dock Cleared" 

--#TYPE       "Chassis Intrusion Event" 
--#SUMMARY    "Unauthorized dock Cleared" 
--#ARGUMENTS  {} 
--#SEVERITY   INFORMATIONAL 

::= { petevts 356229 }
 
     -- Fan Area Intrusion Cleared 
trapChassisFanAreaIntrusionCleared NOTIFICATION-TYPE 
STATUS current
-- ENTERPRISE petevts 
DESCRIPTION  
 "Fan Area Intrusion Cleared" 

--#TYPE       "Chassis Intrusion Event" 
--#SUMMARY    "Fan Area Intrusion Cleared" 
--#ARGUMENTS  {} 
--#SEVERITY   INFORMATIONAL 

::= { petevts 356230 }

--********************** 
--* Platform Security  * 
--********************** 
    -- Secure Mode Violation Attempt 
trapSecureModeViolation NOTIFICATION-TYPE 
STATUS current
-- ENTERPRISE petevts 
DESCRIPTION  
 "Secure Mode Violation Attempt" 

--#TYPE       "Platform Securtiy Violation Attempt Event" 
--#SUMMARY    "Secure Mode Violation Attempt" 
--#ARGUMENTS  {} 
--#SEVERITY   CRITICAL 

::= { petevts 421632 }
 
     -- User Password Violation Attempt 
trapUserPasswordViolation NOTIFICATION-TYPE 
STATUS current
-- ENTERPRISE petevts 
DESCRIPTION  
 "User Password Violation Attempt" 

--#TYPE       "Platform Securtiy Violation Attempt Event" 
--#SUMMARY    "User Password Violation Attempt" 
--#ARGUMENTS  {} 
--#SEVERITY   CRITICAL 

::= { petevts 421633 }

      -- Setup Password Violation Attempt 
trapSetupPasswordViolation NOTIFICATION-TYPE 
STATUS current
-- ENTERPRISE petevts 
DESCRIPTION  
 "Setup Password Violation Attempt" 

--#TYPE       "Platform Securtiy Violation Attempt Event" 
--#SUMMARY    "Setup Password Violation Attempt" 
--#ARGUMENTS  {} 
--#SEVERITY   CRITICAL 

::= { petevts 421634 }
 
       -- Network Boot Password Violation Attempt 
trapNetworkBootPasswordViolation NOTIFICATION-TYPE 
STATUS current
-- ENTERPRISE petevts 
DESCRIPTION  
 "Network Boot Password Violation Attempt" 

--#TYPE       "Platform Securtiy Violation Attempt Event" 
--#SUMMARY    "Network boot Password Violation Attempt" 
--#ARGUMENTS  {} 
--#SEVERITY   CRITICAL 

::= { petevts 421635 }
 
       -- Other Pre-boot Password Violation Attempt 
trapOtherPasswordViolation NOTIFICATION-TYPE 
STATUS current
-- ENTERPRISE petevts 
DESCRIPTION  
 "Other Pre-boot Password Violation Attempt" 

--#TYPE       "Platform Securtiy Violation Attempt Event" 
--#SUMMARY    "Other pre-boot Password Violation Attempt" 
--#ARGUMENTS  {} 
--#SEVERITY   CRITICAL 

::= { petevts 421636 }
 
       -- Out-of-band access Password Violation Attempt 
trapOutOfBandAccessViolation NOTIFICATION-TYPE 
STATUS current
-- ENTERPRISE petevts 
DESCRIPTION  
 "Out-of-band access Violation Attempt" 

--#TYPE       "Platform Securtiy Violation Attempt Event" 
--#SUMMARY    "Out-of-band access Violation Attempt" 
--#ARGUMENTS  {} 
--#SEVERITY   CRITICAL 

::= { petevts 421637 }
 
     -- Secure Mode Violation Attempt Cleared 
trapSecureModeViolationCleared NOTIFICATION-TYPE 
STATUS current
-- ENTERPRISE petevts 
DESCRIPTION  
 "Secure Mode Violation Attempt Cleared" 

--#TYPE       "Platform Securtiy Violation Attempt Event" 
--#SUMMARY    "Secure Mode Violation Attempt Cleared" 
--#ARGUMENTS  {} 
--#SEVERITY   INFORMATIONAL 

::= { petevts 421760 }
 
     -- User Password Violation Attempt Cleared  
trapUserPasswordViolationCleared NOTIFICATION-TYPE 
STATUS current
-- ENTERPRISE petevts 
DESCRIPTION  
 "User Password Violation Attempt Cleared" 

--#TYPE       "Platform Securtiy Violation Attempt Event" 
--#SUMMARY    "User Password Violation Attempt Cleared" 
--#ARGUMENTS  {} 
--#SEVERITY   INFORMATIONAL 

::= { petevts 421761 }

      -- Setup Password Violation Attempt Cleared 
trapSetupPasswordViolationCleared NOTIFICATION-TYPE 
STATUS current
-- ENTERPRISE petevts 
DESCRIPTION  
 "Setup Password Violation Attempt Cleared" 

--#TYPE       "Platform Securtiy Violation Attempt Event" 
--#SUMMARY    "Setup Password Violation Attempt Cleared"  
--#ARGUMENTS  {} 
--#SEVERITY   INFORMATIONAL 

::= { petevts 421762 }
 
       -- Network Boot Password Violation Attempt Cleared 
trapNetworkBootPasswordViolationCleared NOTIFICATION-TYPE 
STATUS current
-- ENTERPRISE petevts 
DESCRIPTION  
 "Network Boot Password Violation Attempt Cleared" 

--#TYPE       "Platform Securtiy Violation Attempt Event" 
--#SUMMARY    "Network boot Password Violation Attempt Cleared" 
--#ARGUMENTS  {} 
--#SEVERITY   INFORMATIONAL 

::= { petevts 421763 }
 
       -- Other Pre-boot Password Violation Attempt Cleared 
trapOtherPasswordViolationCleared NOTIFICATION-TYPE 
STATUS current
-- ENTERPRISE petevts 
DESCRIPTION  
 "Other Pre-boot Password Violation Attempt Cleared" 

--#TYPE       "Platform Securtiy Violation Attempt Event" 
--#SUMMARY    "Other pre-boot Password Violation Attempt Cleared" 
--#ARGUMENTS  {} 
--#SEVERITY   INFORMATIONAL 

::= { petevts 421764 }
 
       -- Out-of-band access Password Violation Attempt Cleared 
trapOutOfBandAccessViolationCleared NOTIFICATION-TYPE 
STATUS current
-- ENTERPRISE petevts 
DESCRIPTION  
 "Out-of-band access Violation Attempt Cleared" 

--#TYPE       "Platform Securtiy Violation Attempt Event" 
--#SUMMARY    "Out-of-band access Violation Attempt Cleared" 
--#ARGUMENTS  {} 
--#SEVERITY   INFORMATIONAL 

::= { petevts 421765 }
 
 
--********************** 
--* Processor  * 
--********************** 

-- Processor internal error 
trapProcessorInternalError NOTIFICATION-TYPE 
STATUS current
-- ENTERPRISE petevts 
DESCRIPTION  
 "Processor Internal Error" 

--#TYPE       "Processor Event" 
--#SUMMARY    "Processor Internal Error" 
--#ARGUMENTS  {} 
--#SEVERITY   CRITICAL 

::= { petevts 487168 }
 
-- Processor Thermal Trip 
trapProcessorThermalTrip NOTIFICATION-TYPE 
STATUS current
-- ENTERPRISE petevts 
DESCRIPTION  
"Processor Thermal Trip (Over Temperature Shutdown)" 

--#TYPE       "Processor Event" 
--#SUMMARY    "Processor Thermal Trip (Over Temperature Shutdown)" 
--#ARGUMENTS  {} 
--#SEVERITY   CRITICAL 

::= { petevts 487169 }

--Processor Fault Resilient Booting (FRB) 1 / Built-in self test (BIST) Error 
trapProcessorBistError NOTIFICATION-TYPE 
STATUS current
-- ENTERPRISE petevts 
DESCRIPTION  
 "Processor Fault Resilient Booting (FRB) 1 / BIST (Built In Self Test) Failure" 

--#TYPE       "Processor Event" 
--#SUMMARY    "Processor Fault Resilient Booting (FRB) 1 / Processor BIST (Built In Self Test) Failure" 
--#ARGUMENTS  {} 
--#SEVERITY   CRITICAL 

::= { petevts 487170 }

--Processor Fault Resilient Booting (FRB) 2 / Hang in Power On Self Test (POST) 
trapProcessorFRB2Failure NOTIFICATION-TYPE 
STATUS current
-- ENTERPRISE petevts 
DESCRIPTION  
 "Processor Fault Resilient Booting (FRB) 2 / Hang in Power On Self Test (POST) Failure" 

--#TYPE       "Processor Event" 
--#SUMMARY    "Processor Fault Resilient Booting (FRB) 2 / Hang in Power On Self Test (POST) Failure" 
--#ARGUMENTS  {} 
--#SEVERITY   CRITICAL  

::= { petevts 487171 }

--Processor Fault Resilient Booting (FRB) 3 / Processor Setup / Initialization Failure 
trapProcessorFRB3Failure NOTIFICATION-TYPE 
STATUS current
-- ENTERPRISE petevts 
DESCRIPTION  
 "Processor Fault Resilient Booting (FRB) 3 / Processor Setup / Initialization Failure" 

--#TYPE	"Processor Event" 
--#SUMMARY    "Processor Fault Resilient Booting (FRB) 3 / Processor Setup / Initialization Failure" 
--#ARGUMENTS  {} 
--#SEVERITY   CRITICAL 

::= { petevts 487172 }

--Processor config error 
trapProcessorConfigError NOTIFICATION-TYPE 
STATUS current
-- ENTERPRISE petevts 
DESCRIPTION  
 "Processor Configuration Error" 

--#TYPE       "Processor Event" 
--#SUMMARY    "Processor Configuration Error" 
--#ARGUMENTS  {} 
--#SEVERITY   CRITICAL 

::= { petevts 487173 }
 
-- SM BIOS Uncorrectable CPU-complex Error 
trapSMPIOSUncorrectableCPUComplexError NOTIFICATION-TYPE 
STATUS current
-- ENTERPRISE petevts 
DESCRIPTION  
 "SM BIOS Uncorrectable CPU-complex Error" 

--#TYPE       "Processor Event" 
--#SUMMARY    "SM BIOS Uncorrectable CPU-complex Error" 
--#ARGUMENTS  {} 
--#SEVERITY   CRITICAL 

::= { petevts 487174 }
 
 -- Processor Presence Detected 
trapProcessorPresenceDetected NOTIFICATION-TYPE 
STATUS current
-- ENTERPRISE petevts 
DESCRIPTION  
 "Processor Presence Detected" 

--#TYPE       "Processor Event" 
--#SUMMARY    "Processor Presence Detected" 
--#ARGUMENTS  {} 
--#SEVERITY   INFORMATIONAL 

::= { petevts 487175 }
 
  -- Processor Disabled 
trapProcessorDisabled NOTIFICATION-TYPE 
STATUS current
-- ENTERPRISE petevts 
DESCRIPTION  
 "Processor Disabled" 

--#TYPE       "Processor Event" 
--#SUMMARY    "Processor Disabled" 
--#ARGUMENTS  {} 
--#SEVERITY   INFORMATIONAL 

::= { petevts 487176 }
 
  -- Terminator Presence Detected 
trapTerminatorresenceDetected NOTIFICATION-TYPE 
STATUS current
-- ENTERPRISE petevts 
DESCRIPTION  
 "Terminator Presence Detected" 

--#TYPE       "Processor Event" 
--#SUMMARY    "Terminator Presence Detected" 
--#ARGUMENTS  {} 
--#SEVERITY   INFORMATIONAL 

::= { petevts 487177 }
 
-- Processor throttle. 
trapProcessorThrottle NOTIFICATION-TYPE 
STATUS current
-- ENTERPRISE petevts 
DESCRIPTION  
 "Processor Throttled (Processor Speed Reduced)" 

--#TYPE       "Processor Event" 
--#SUMMARY    "Processor Throttled (Processor Speed Reduced)" 
--#ARGUMENTS  {} 
--#SEVERITY   WARNING 

::= { petevts 487178 }
 
-- Processor internal error cleared 
trapProcessorInternalErrorCleared NOTIFICATION-TYPE 
STATUS current
-- ENTERPRISE petevts 
DESCRIPTION  
 "Processor Internal Error Cleared" 

--#TYPE       "Processor Event" 
--#SUMMARY    "Processor Internal Error Cleared" 
--#ARGUMENTS  {} 
--#SEVERITY   INFORMATIONAL 

::= { petevts 487296 }

--Processor Back to normal from Thermal Trip 
trapProcessorThermalTripCleared NOTIFICATION-TYPE 
STATUS current
-- ENTERPRISE petevts 
DESCRIPTION  
 "Processor Thermal Trip (Over Temperature Shutdown) Cleared" 

--#TYPE       "Processor Event" 
--#SUMMARY    "Processor Thermal Trip (Over Temperature Shutdown) Cleared" 
--#ARGUMENTS  {} 
--#SEVERITY   INFORMATIONAL 

::= { petevts 487297 }
 
-- Processor BIST Error cleared 
trapProcessorBistErrorCleared NOTIFICATION-TYPE 
STATUS current
-- ENTERPRISE petevts 
DESCRIPTION  
 "Processor BIST (Built In Self Test) Failure Cleared" 

--#TYPE       "Processor Event" 
--#SUMMARY    "Processor BIST (Built In Self Test) Failure Cleared" 
--#ARGUMENTS  {} 
--#SEVERITY   INFORMATIONAL 

::= { petevts 487298 }

--Processor Fault Resilient Booting (FRB) 2 / Hang in Power On Self Test (POST) Cleared 
trapProcessorFRB2FailureCleared NOTIFICATION-TYPE 
STATUS current
-- ENTERPRISE petevts 
DESCRIPTION  
 "Processor Fault Resilient Booting (FRB) 2 / Hang in Power On Self Test (POST) Failure Cleared" 

--#TYPE       "Processor Event" 
--#SUMMARY    "Processor Fault Resilient Booting (FRB) 2 / Hang in Power On Self Test (POST) Failure Cleared" 
--#ARGUMENTS  {} 
--#SEVERITY   INFORMATIONAL  

::= { petevts 487299 }
 
-- Processor Fault Resilient Booting (FRB) 3 / Processor Setup / Initialization Failure Cleared 
trapProcessorFRB3FailureCleared NOTIFICATION-TYPE 
STATUS current
-- ENTERPRISE petevts 
DESCRIPTION  
 "Processor Fault Resilient Booting (FRB) 3 / Processor Setup / Initialization Failure Cleared" 

--#TYPE	"Processor Event" 
--#SUMMARY    "Processor Fault Resilient Booting (FRB) 3 / Processor Setup / Initialization Failure Cleared" 
--#ARGUMENTS  {} 
--#SEVERITY   INFORMATIONAL 

::= { petevts 487300 }
 
-- Processor config error cleared 
trapProcessorConfigErrorCleared NOTIFICATION-TYPE 
STATUS current
-- ENTERPRISE petevts 
DESCRIPTION  
 "Processor Configuration Error Cleared" 

--#TYPE       "Processor Event" 
--#SUMMARY    "Processor Configuration Error Cleared" 
--#ARGUMENTS  {} 
--#SEVERITY   INFORMATIONAL 

::= { petevts 487301 }
 
-- SM BIOS Uncorrectable CPU-complex Error Cleared 
trapSMPIOSUncorrectableCPUComplexErrorCleared NOTIFICATION-TYPE 
STATUS current
-- ENTERPRISE petevts 
DESCRIPTION  
 "SM BIOS Uncorrectable CPU-complex Error Cleared" 

--#TYPE       "Processor Event" 
--#SUMMARY    "SM BIOS Uncorrectable CPU-complex Error Cleared" 
--#ARGUMENTS  {} 
--#SEVERITY   CRITICAL 

::= { petevts 487302 }
 
-- Processor return to normal from throttled 
trapProcessorThrottleCleared NOTIFICATION-TYPE 
STATUS current
-- ENTERPRISE petevts 
DESCRIPTION  
 "Processor Throttle Cleared (Normal Processor Speed)" 

--#TYPE       "Processor Event" 
--#SUMMARY    "Processor Throttle Cleared (Normal Processor Speed)" 
--#ARGUMENTS  {} 
--#SEVERITY   INFORMATIONAL 

::= { petevts 487306 }
  
-- Correctable Machine Check Error Cleared 
trapCorrectableMachineCheckErrorCleared NOTIFICATION-TYPE 
STATUS current
-- ENTERPRISE petevts 
DESCRIPTION  
 "Correctable Machine Check Error Cleared" 

--#TYPE       "Processor Event" 
--#SUMMARY    "Correctable Machine Check Error Cleared" 
--#ARGUMENTS  {} 
--#SEVERITY   INFORMATIONAL 

::= { petevts 487308 }
 
-- ********************************************** 
-- *	Power Supply 				* 
-- ********************************************** 

-- Power Supply State Deasserted 
trapPowerSupplyStateDeasserted NOTIFICATION-TYPE 
STATUS current
-- ENTERPRISE petevts 
DESCRIPTION  
 "Power Supply is disconnected from AC Power." 

--#TYPE       "Power Supply Event" 
--#SUMMARY    "Power Supply is disconnected from AC Power." 
--#ARGUMENTS  {} 
--#SEVERITY   CRITICAL 

::= { petevts 525056 }

--Power Supply State Asserted 
trapPowerSupplyStateAsserted NOTIFICATION-TYPE 
STATUS current
-- ENTERPRISE petevts 
DESCRIPTION  
 "Power Supply is connected to AC Power." 

--#TYPE       "Power Supply Event" 
--#SUMMARY    "Power Supply is connected to AC Power." 
--#ARGUMENTS  {} 
--#SEVERITY   INFORMATIONAL 

::= { petevts 525057 }

--Predictive Failure Deasserted 
trapPowerSupplyPredictiveFailureAsserted NOTIFICATION-TYPE 
STATUS current
-- ENTERPRISE petevts 
DESCRIPTION  
 "Power Supply Predictive Failure Deasserted" 

--#TYPE       "Power Supply Event" 
--#SUMMARY    "Power Supply Predictive Failure Deasserted" 
--#ARGUMENTS  {} 
--#SEVERITY   CRITICAL 

::= { petevts 525313 }

--Predictive Failure Asserted 
trapPowerSupplyPredictiveFailureDeasserted NOTIFICATION-TYPE 
STATUS current
-- ENTERPRISE petevts 
DESCRIPTION  
 "Power Supply Predictive Failure Asserted" 

--#TYPE       "Power Supply Event" 
--#SUMMARY    "Power Supply Predictive Failure Asserted" 
--#ARGUMENTS  {} 
--#SEVERITY   INFORMATIONAL 

::= { petevts 525312 }
 
-- Power Supply Full Redundancy  
trapPowerSupplyFullRedundancy NOTIFICATION-TYPE 
STATUS current
-- ENTERPRISE petevts 
DESCRIPTION  
 "Power Supply Redundancy Has Returned to Normal" 

--#TYPE       "Power Supply Event" 
--#SUMMARY    "Power Supply Redundancy Has Returned to Normal" 
--#ARGUMENTS  {} 
--#SEVERITY   INFORMATIONAL 

::= { petevts 527104 }

--Power Supply Redundancy lost  
trapPowerSupplyRedundancyLost NOTIFICATION-TYPE 
STATUS current
-- ENTERPRISE petevts 
DESCRIPTION  
 "Power Supply Redundancy has been Lost" 

--#TYPE       "Power Supply Event" 
--#SUMMARY    "Power Supply Redundancy has been Lost" 
--#ARGUMENTS  {} 
--#SEVERITY   CRITICAL 

::= { petevts 527105 }

--Power Supply Redundancy degraded 
trapPowerSupplyRedundancyDegraded NOTIFICATION-TYPE 
STATUS current
-- ENTERPRISE petevts 
DESCRIPTION  
 "Power Supply Redundancy is in a degraded state" 

--#TYPE       "Power Supply Event" 
--#SUMMARY    "Power Supply Redundancy is in a degraded state" 
--#ARGUMENTS  {} 
--#SEVERITY   WARNING 

::= { petevts 527106 }

--Power Supply presence detected 
trapPowerSupplyPresenceDeteced NOTIFICATION-TYPE 
STATUS current
-- ENTERPRISE petevts 
DESCRIPTION  
 "Power Supply Inserted" 

--#TYPE       "Power Supply Event" 
--#SUMMARY    "Power Supply Inserted" 
--#ARGUMENTS  {} 
--#SEVERITY   INFORMATIONAL 

::= { petevts 552704 }

trapPowerSupplyFailureDetected NOTIFICATION-TYPE 
STATUS current
-- ENTERPRISE petevts 
DESCRIPTION  
 "Power supply Failure detected" 

--#TYPE       "Power Supply Event" 
--#SUMMARY    "Power Supply failure detected" 
--#ARGUMENTS  {} 
--#SEVERITY   CRITICAL 

::= { petevts 552705 }

trapPowerSupplyWarning NOTIFICATION-TYPE 
STATUS current
-- ENTERPRISE petevts 
DESCRIPTION  
 "Power supply Warning" 

--#TYPE       "Power Supply Event" 
--#SUMMARY    "Power Supply Warning" 
--#ARGUMENTS  {} 
--#SEVERITY   WARNING 

::= { petevts 552706 }

--AC Lost 
trapPowerSupplyACLost NOTIFICATION-TYPE 
STATUS current
-- ENTERPRISE petevts 
DESCRIPTION  
 "Power Supply AC Lost" 

--#TYPE       "Power Supply Event" 
--#SUMMARY    "Power Supply AC Lost" 
--#ARGUMENTS  {} 
--#SEVERITY   CRITICAL 

::= { petevts 552707 }

 -- Power Supply input lost or out-of-range 
trapPowerSupplyInputLost NOTIFICATION-TYPE 
STATUS current
-- ENTERPRISE petevts 
DESCRIPTION  
 "Power Supply input lost or out-of-range" 

--#TYPE       "Power Supply Event" 
--#SUMMARY    "Power Supply input lost or out-of-range" 
--#ARGUMENTS  {} 
--#SEVERITY   CRITICAL 

::= { petevts 552708 }
 
  -- Power Supply input out-of-range, but present 
trapPowerSupplyInputOutOfRange NOTIFICATION-TYPE 
STATUS current
-- ENTERPRISE petevts 
DESCRIPTION  
 "Power Supply input out-of-range, but present" 

--#TYPE       "Power Supply Event" 
--#SUMMARY    "Power Supply input out-of-range, but present" 
--#ARGUMENTS  {} 
--#SEVERITY   CRITICAL 

::= { petevts 552709 }
 
  -- Configuration error 
trapPowerSupplyConfigError NOTIFICATION-TYPE 
STATUS current
-- ENTERPRISE petevts 
DESCRIPTION  
 "Power Supply Configuration error" 

--#TYPE       "Power Supply Event" 
--#SUMMARY    "Power Supply Configuration error" 
--#ARGUMENTS  {} 
--#SEVERITY   CRITICAL 

::= { petevts 552710 }
 
-- Power Supply removed 
trapPowerSupplyPresenceRemoved NOTIFICATION-TYPE 
STATUS current
-- ENTERPRISE petevts 
DESCRIPTION  
"Power Supply Removed" 

--#TYPE       "Power Supply Event" 
--#SUMMARY    "Power Supply Removed" 
--#ARGUMENTS  {} 
--#SEVERITY   WARNING 

::= { petevts 552832 }

--Back to normal from failure 
trapPowerSupplyFailureCleared NOTIFICATION-TYPE 
STATUS current
-- ENTERPRISE petevts 
DESCRIPTION  
 "Power Supply Failure Cleared" 

--#TYPE       "Power Supply Event" 
--#SUMMARY    "Power Supply Failure Cleared" 
--#ARGUMENTS  {} 
--#SEVERITY   INFORMATIONAL 

::= { petevts 552833 }

--Predictive Failure cleared  
trapPowerSupplyWarningCleared NOTIFICATION-TYPE 
STATUS current
-- ENTERPRISE petevts 
DESCRIPTION  
 "Power Supply Warning Cleared" 

--#TYPE       "Power Supply Event" 
--#SUMMARY    "Power Supply Warning Cleared" 
--#ARGUMENTS  {} 
--#SEVERITY   INFORMATIONAL 

::= { petevts 552834 }

--AC Back 
trapPowerSupplyACBack NOTIFICATION-TYPE 
STATUS current
-- ENTERPRISE petevts 
DESCRIPTION  
 "Power Supply AC Restored" 

--#TYPE       "Power Supply Event" 
--#SUMMARY    "Power Supply AC Restored" 
--#ARGUMENTS  {} 
--#SEVERITY   INFORMATIONAL 

::= { petevts 552835 }

 -- Power Supply input lost or out-of-range Restored 
trapPowerSupplyInputBack NOTIFICATION-TYPE 
STATUS current
-- ENTERPRISE petevts 
DESCRIPTION  
 "Power Supply input lost or out-of-range Restored" 

--#TYPE       "Power Supply Event" 
--#SUMMARY    "Power Supply input lost or out-of-range Restored" 
--#ARGUMENTS  {} 
--#SEVERITY   INFORMATIONAL 

::= { petevts 552836 }
 
  -- Power Supply input out-of-range is restored 
trapPowerSupplyInputOutOfRangeRestored NOTIFICATION-TYPE 
STATUS current
-- ENTERPRISE petevts 
DESCRIPTION  
 "Power Supply input out-of-range restored"  

--#TYPE       "Power Supply Event" 
--#SUMMARY    "Power Supply input out-of-range restored" 
--#ARGUMENTS  {} 
--#SEVERITY   INFORMATIONAL 

::= { petevts 552837 }
 
  -- Configuration error Cleared 
trapPowerSupplyConfigErrorCleared NOTIFICATION-TYPE 
STATUS current
-- ENTERPRISE petevts 
DESCRIPTION  
 "Power Supply Configuration error Cleared" 

--#TYPE       "Power Supply Event" 
--#SUMMARY    "Power Supply Configuration error Cleared" 
--#ARGUMENTS  {} 
--#SEVERITY   CRITICAL 

::= { petevts 552838 }

--********************************************** 
-- *	Power Unit 				* 
-- ********************************************** 

-- Power Good Sensor events Deasserted 
trapPowerUnitStateDeasserted NOTIFICATION-TYPE 
STATUS current
-- ENTERPRISE petevts 
DESCRIPTION 
 "Run-time power fault has occurred. This state indicates 
  that one or more DC-DC converter have failed or are not operating 
  within nominal specifications." 

--#TYPE         "Power Unit Event" 
--#SUMMARY      "Run-time power fault has occurred." 
--#ARGUMENTS    {} 
--#SEVERITY     CRITICAL 

::= { petevts 590592 }

--Power Good Sensor events Asserted 
trapPowerUnitStateAsserted NOTIFICATION-TYPE 
STATUS current
-- ENTERPRISE petevts 
DESCRIPTION 
 "Host power-on sequence has been completed successfully" 

--#TYPE         "Power Unit Event" 
--#SUMMARY      "Host power-on sequence has been completed successfully." 
--#ARGUMENTS    {} 
--#SEVERITY     INFORMATIONAL 

::= { petevts 590593 }

-- Power Unit Redundancy OK  
trapPowerUnitRedundancyOk NOTIFICATION-TYPE 
STATUS current
-- ENTERPRISE petevts 
DESCRIPTION  
 "Power Unit Redundancy has been restored" 

--#TYPE       "Power Unit Event" 
--#SUMMARY    "Power Unit Redundancy has been restored" 
--#ARGUMENTS  {} 
--#SEVERITY   INFORMATIONAL 

::= { petevts 592640 }

-- Power Unit Redundancy lost  
trapPowerUnitRedundancyLost NOTIFICATION-TYPE 
STATUS current
-- ENTERPRISE petevts 
DESCRIPTION  
 "Power Unit Redundancy has been Lost" 

--#TYPE       "Power Unit Event" 
--#SUMMARY    "Power Unit Redundancy has been Lost" 
--#ARGUMENTS  {} 
--#SEVERITY   CRITICAL 

::= { petevts 592641 }

-- Power Off 
trapPowerUnitPowerOff NOTIFICATION-TYPE 
STATUS current
-- ENTERPRISE petevts 
DESCRIPTION 
 "Power unit is off." 

--#TYPE       "Power unit event" 
--#SUMMARY    "Power unit is off." 
--#ARGUMENTS  {} 
--#SEVERITY   INFORMATIONAL 

::= { petevts 618240 }
 
-- Power Cycle 
trapPowerUnitPowerCycle NOTIFICATION-TYPE 
STATUS current
-- ENTERPRISE petevts 
DESCRIPTION 
 "Power unit is power cycled" 

--#TYPE       "Power unit event" 
--#SUMMARY    "Power unit is power cycled" 
--#ARGUMENTS  {} 
--#SEVERITY   INFORMATIONAL 

::= { petevts 618241 }
 
-- 240VA Power Down 
trapPowerUnit240VAPowerDown NOTIFICATION-TYPE 
STATUS current
-- ENTERPRISE petevts 
DESCRIPTION 
 "Power unit 240VA Power Down" 

--#TYPE       "Power unit event" 
--#SUMMARY    "Power unit 240VA Power Down" 
--#ARGUMENTS  {} 
--#SEVERITY   INFORMATIONAL 
 
::= { petevts 618242 }
 
 -- Interlock Power Down 
trapPowerUnitInterlockPowerDown NOTIFICATION-TYPE 
STATUS current
-- ENTERPRISE petevts 
DESCRIPTION 
 "Power unit Interlock Power Down" 

--#TYPE       "Power unit event" 
--#SUMMARY    "Power unit Interlock Power Down" 
--#ARGUMENTS  {} 
--#SEVERITY   INFORMATIONAL 
 
::= { petevts 618243 }
 
  -- AC lost / Power input lost 
trapPowerUnitACLost NOTIFICATION-TYPE 
STATUS current
-- ENTERPRISE petevts 
DESCRIPTION 
 "Power unit AC lost / Power input lost" 

--#TYPE       "Power unit event" 
--#SUMMARY    "Power unit AC lost / Power input lost" 
--#ARGUMENTS  {} 
--#SEVERITY   INFORMATIONAL 
 
::= { petevts 618244 }
 
   -- Soft Power Control Failure 
trapPowerUnitSoftPowerControlFail NOTIFICATION-TYPE 
STATUS current
-- ENTERPRISE petevts 
DESCRIPTION 
 "Soft Power Control Failure" 

--#TYPE       "Power unit event" 
--#SUMMARY    "Soft Power Control Failure" 
--#ARGUMENTS  {} 
--#SEVERITY   INFORMATIONAL 
 
::= { petevts 618245 }
 
-- Power Unit Failure detected 
trapPowerUnitFailure NOTIFICATION-TYPE 
STATUS current
-- ENTERPRISE petevts 
DESCRIPTION 
 "Power Unit Failure detected" 

--#TYPE       "Power unit event" 
--#SUMMARY    "Power Unit Failure detected" 
--#ARGUMENTS  {} 
--#SEVERITY   INFORMATIONAL 
 
::= { petevts 618246 }
 
-- Predictive Failure 
trapPowerUnitPredictiveFailure NOTIFICATION-TYPE 
STATUS current
-- ENTERPRISE petevts 
DESCRIPTION 
 "Power Unit Predictive Failure" 

--#TYPE       "Power unit event" 
--#SUMMARY    "Power Unit Predictive Failure" 
--#ARGUMENTS  {} 
--#SEVERITY   INFORMATIONAL 
 
::= { petevts 618247 }
 
-- Power Unit On 
trapPowerUnitPowerOn NOTIFICATION-TYPE 
STATUS current
-- ENTERPRISE petevts 
DESCRIPTION 
 "Power Unit is on." 

--#TYPE       "Power Unit event" 
--#SUMMARY    "Power Unit is on." 
--#ARGUMENTS  {} 
--#SEVERITY   INFORMATIONAL 

::= { petevts 618368 }
 
-- Power Cycle Completed 
 
trapPowerUnitPowerCycleCompleted NOTIFICATION-TYPE 
STATUS current
-- ENTERPRISE petevts 
DESCRIPTION 
 "Power unit - Power Cycle Completed" 

--#TYPE       "Power unit event" 
--#SUMMARY    "Power unit - Power Cycle Completed" 
--#ARGUMENTS  {} 
--#SEVERITY   INFORMATIONAL 

::= { petevts 618369 }
 
-- 240VA Power Down 
trapPowerUnit240VAPowerUp NOTIFICATION-TYPE 
STATUS current
-- ENTERPRISE petevts 
DESCRIPTION 
 "Power unit 240VA Power Up" 

--#TYPE       "Power unit event" 
--#SUMMARY    "Power unit 240VA Power Up" 
--#ARGUMENTS  {} 
--#SEVERITY   INFORMATIONAL 
 
::= { petevts 618370 }
 
 -- Interlock Power Up 
trapPowerUnitInterlockPowerUp NOTIFICATION-TYPE 
STATUS current
-- ENTERPRISE petevts 
DESCRIPTION 
 "Power unit Interlock Power Up" 

--#TYPE       "Power unit event" 
--#SUMMARY    "Power unit Interlock Power Up" 
--#ARGUMENTS  {} 
--#SEVERITY   INFORMATIONAL 
 
::= { petevts 618371 }
 
  -- AC/Power input restored 
trapPowerUnitACRestored NOTIFICATION-TYPE 
STATUS current
-- ENTERPRISE petevts 
DESCRIPTION 
 "Power unit AC/Power input restored" 

--#TYPE       "Power unit event" 
--#SUMMARY    "Power unit AC/Power input restored" 
--#ARGUMENTS  {} 
--#SEVERITY   INFORMATIONAL 
 
::= { petevts 618372 }
 
   -- Soft Power Control Failure Cleared 
trapPowerUnitSoftPowerControlFailCleared NOTIFICATION-TYPE 
STATUS current
-- ENTERPRISE petevts 
DESCRIPTION 
 "Soft Power Control Failure Cleared" 

--#TYPE       "Power unit event" 
--#SUMMARY    "Soft Power Control Failure Cleared" 
--#ARGUMENTS  {} 
--#SEVERITY   INFORMATIONAL 
 
::= { petevts 618373 }
 
-- Power Unit Failure Cleared 
trapPowerUnitFailureCleared NOTIFICATION-TYPE 
STATUS current
-- ENTERPRISE petevts 
DESCRIPTION 
 "Power Unit Failure Cleared" 

--#TYPE       "Power unit event" 
--#SUMMARY    "Power Unit Failure Cleared" 
--#ARGUMENTS  {} 
--#SEVERITY   INFORMATIONAL 
 
::= { petevts 618374 }
 
-- Predictive Failure Cleared 
trapPowerUnitPredictiveFailureCleared NOTIFICATION-TYPE 
STATUS current
-- ENTERPRISE petevts 
DESCRIPTION 
 "Power Unit Predictive Failure Cleared" 

--#TYPE       "Power unit event" 
--#SUMMARY    "Power Unit Predictive Failure Cleared" 
--#ARGUMENTS  {} 
--#SEVERITY   INFORMATIONAL 
 
::= { petevts 618375 }

-- ********************************************** 
-- *		Cooling Device 			* 
-- ********************************************** 

-- Cooling Device speed has decreased below lower non-critical threshold 
trapCoolingDeviceUnderSpeedWarningLow NOTIFICATION-TYPE 
STATUS current
-- ENTERPRISE petevts 
DESCRIPTION  
"Cooling Device Under Speed Warning (Lower non-critical, going low)" 

--#TYPE       "Cooling Device Event" 
--#SUMMARY    "Cooling Device Under Speed Warning (Lower non-critical, going low)" 
--#ARGUMENTS  {} 
--#SEVERITY   WARNING 

::= { petevts 655616 }
 
-- Cooling Device speed has increased above lower non-critical threshold 
trapCoolingDeviceUnderSpeedWarningHigh NOTIFICATION-TYPE 
STATUS current
-- ENTERPRISE petevts 
DESCRIPTION  
"Cooling Device Under Speed Warning (Lower non-critical, going high)" 

--#TYPE       "Cooling Device Event" 
--#SUMMARY    "Cooling Device Under Speed Warning (Lower non-critical, going high)" 
--#ARGUMENTS  {} 
--#SEVERITY   WARNING 

::= { petevts 655617 }
 
-- Cooling Device speed has decreased below lower critical threshold 
trapCoolingDeviceUnderSpeedCriticalLow NOTIFICATION-TYPE 
STATUS current
-- ENTERPRISE petevts 
DESCRIPTION  
"Critical Cooling Device Under Speed problem (Lower critical, going low)" 

--#TYPE       "Cooling Device Event" 
--#SUMMARY    "Cooling Device Under Speed Warning (Lower critical, going low)" 
--#ARGUMENTS  {} 
--#SEVERITY   CRITICAL 

::= { petevts 655618 }
 
 -- Cooling Device speed has increased above lower critical threshold 
trapCoolingDeviceUnderSpeedCriticalHigh NOTIFICATION-TYPE 
STATUS current
-- ENTERPRISE petevts 
DESCRIPTION  
"Critical Cooling Device Under Speed problem (Lower critical, going high)" 

--#TYPE       "Cooling Device Event" 
--#SUMMARY    "Cooling Device Under Speed Warning (Lower critical, going high)" 
--#ARGUMENTS  {} 
--#SEVERITY   CRITICAL 

::= { petevts 655619 }
 
 -- Cooling Device speed has decreased below lower non-recoverable threshold 
trapCoolingDeviceUnderSpeedNonRecoverableLow NOTIFICATION-TYPE 
STATUS current
-- ENTERPRISE petevts 
DESCRIPTION  
"Critical Cooling Device Under Speed problem (Lower non-recoverable, going low)" 

--#TYPE       "Cooling Device Event" 
--#SUMMARY    "Cooling Device Under Speed Warning (Lower non-recoverable, going low)" 
--#ARGUMENTS  {} 
--#SEVERITY   CRITICAL 

::= { petevts 655620 }
 
 -- Cooling Device speed has increased above lower non-recoverable threshold 
trapCoolingDeviceUnderSpeedNonRecoverableHigh NOTIFICATION-TYPE 
STATUS current
-- ENTERPRISE petevts 
DESCRIPTION  
"Critical Cooling Device Under Speed problem (Lower non-recoverable, going high)" 

--#TYPE       "Cooling Device Event" 
--#SUMMARY    "Cooling Device Under Speed Warning (Lower non-recoverable, going high)" 
--#ARGUMENTS  {} 
--#SEVERITY   CRITICAL 

::= { petevts 655621 }
 
-- Cooling Device speed has decreased below Upper non-critical threshold 
trapCoolingDeviceOverSpeedWarningLow NOTIFICATION-TYPE 
STATUS current
-- ENTERPRISE petevts 
DESCRIPTION  
"Cooling Device Over Speed Warning (Upper non-critical, going low)" 

--#TYPE       "Cooling Device Event" 
--#SUMMARY    "Cooling Device Over Speed Warning (Upper non-critical, going low)" 
--#ARGUMENTS  {} 
--#SEVERITY   WARNING 

::= { petevts 655622 }
 
-- Cooling Device speed has increased above upper non-critical threshold. 
trapCoolingDeviceOverSpeedWarningHigh NOTIFICATION-TYPE 
STATUS current
-- ENTERPRISE petevts 
DESCRIPTION  
"Cooling Device Over Speed Warning (Upper non-critical, going high)" 

--#TYPE       "Cooling Device Event" 
--#SUMMARY    "Cooling Device Over Speed Warning (Upper non-critical, going high)" 
--#ARGUMENTS  {} 
--#SEVERITY   WARNING 

::= { petevts 655623 }
 
-- Cooling Device speed has decreased below Upper critical threshold 
trapCoolingDeviceOverSpeedCriticalLow NOTIFICATION-TYPE 
STATUS current
-- ENTERPRISE petevts 
DESCRIPTION  
"Critical Cooling Device Over Speed problem (Upper critical, going low)" 

--#TYPE       "Cooling Device Event" 
--#SUMMARY    "Cooling Device Over Speed Warning (Upper critical, going low)" 
--#ARGUMENTS  {} 
--#SEVERITY   CRITICAL 

::= { petevts 655624 }
 
 -- Cooling Device speed has increased above Upper critical threshold 
trapCoolingDeviceOverSpeedCriticalHigh NOTIFICATION-TYPE 
STATUS current
-- ENTERPRISE petevts 
DESCRIPTION  
"Critical Cooling Device Over Speed problem (Upper critical, going high)" 

--#TYPE       "Cooling Device Event" 
--#SUMMARY    "Cooling Device Over Speed Warning (Upper critical, going high)" 
--#ARGUMENTS  {} 
--#SEVERITY   CRITICAL 

::= { petevts 655625 }
 
 -- Cooling Device speed has decreased below Upper non-recoverable threshold 
trapCoolingDeviceOverSpeedNonRecoverableLow NOTIFICATION-TYPE 
STATUS current
-- ENTERPRISE petevts 
DESCRIPTION  
"Critical Cooling Device Over Speed problem (Upper non-recoverable, going low)" 

--#TYPE       "Cooling Device Event" 
--#SUMMARY    "Cooling Device Over Speed Warning (Upper non-recoverable, going low)" 
--#ARGUMENTS  {} 
--#SEVERITY   CRITICAL 

::= { petevts 655626 }
 
 -- Cooling Device speed has increased above Upper non-recoverable threshold 
trapCoolingDeviceOverSpeedNonRecoverableHigh NOTIFICATION-TYPE 
STATUS current
-- ENTERPRISE petevts 
DESCRIPTION  
"Critical Cooling Device Over Speed problem (Upper non-recoverable, going high)" 

--#TYPE       "Cooling Device Event" 
--#SUMMARY    "Cooling Device Under Speed Warning (Upper non-recoverable, going high)" 
--#ARGUMENTS  {} 
--#SEVERITY   CRITICAL 

::= { petevts 655627 }
 
-- Cooling Device speed decreased below lower non-critical threshold Cleared 
trapCoolingDeviceUnderSpeedWarningLowCleared NOTIFICATION-TYPE 
STATUS current
-- ENTERPRISE petevts 
DESCRIPTION  
"Cooling Device Under Speed Warning (Lower non-critical, going low) Cleared" 

--#TYPE       "Cooling Device Event" 
--#SUMMARY    "Cooling Device Under Speed Warning (Lower non-critical, going low) Cleared" 
--#ARGUMENTS  {} 
--#SEVERITY   INFORMATIONAL 

::= { petevts 655744 }
 
-- Cooling Device speed increased above lower non-critical threshold Cleared 
trapCoolingDeviceUnderSpeedWarningHighCleared NOTIFICATION-TYPE 
STATUS current
-- ENTERPRISE petevts 
DESCRIPTION  
"Cooling Device Under Speed Warning (Lower non-critical, going high)Cleared" 

--#TYPE       "Cooling Device Event" 
--#SUMMARY    "Cooling Device Under Speed Warning (Lower non-critical, going high)Cleared" 
--#ARGUMENTS  {} 
--#SEVERITY   INFORMATIONAL 

::= { petevts 655745 }
 
-- Cooling Device speed decreased below lower critical threshold Cleared 
trapCoolingDeviceUnderSpeedCriticalLowCleared NOTIFICATION-TYPE 
STATUS current
-- ENTERPRISE petevts 
DESCRIPTION  
"Critical Cooling Device Under Speed problem (Lower critical, going low)Cleared" 

--#TYPE       "Cooling Device Event" 
--#SUMMARY    "Cooling Device Under Speed Warning (Lower critical, going low)Cleared" 
--#ARGUMENTS  {} 
--#SEVERITY   INFORMATIONAL 

::= { petevts 655746 }
 
 -- Cooling Device speed increased above lower critical threshold Cleared 
trapCoolingDeviceUnderSpeedCriticalHighCleared NOTIFICATION-TYPE 
STATUS current
-- ENTERPRISE petevts 
DESCRIPTION  
"Critical Cooling Device Under Speed problem (Lower critical, going high) Cleared" 

--#TYPE       "Cooling Device Event" 
--#SUMMARY    "Cooling Device Under Speed Warning (Lower critical, going high) Cleared" 
--#ARGUMENTS  {} 
--#SEVERITY   INFORMATIONAL 

::= { petevts 655747 }
 
 -- Cooling Device speed decreased below lower non-recoverable threshold Cleared 
trapCoolingDeviceUnderSpeedNonRecoverableLowCleared NOTIFICATION-TYPE 
STATUS current
-- ENTERPRISE petevts 
DESCRIPTION  
"Critical Cooling Device Under Speed problem (Lower non-recoverable, going low)Cleared" 

--#TYPE       "Cooling Device Event" 
--#SUMMARY    "Cooling Device Under Speed Warning (Lower non-recoverable, going low)Cleared" 
--#ARGUMENTS  {} 
--#SEVERITY   INFORMATIONAL 

::= { petevts 655748 }
 
 -- Cooling Device speed increased above lower non-recoverable threshold Cleared 
trapCoolingDeviceUnderSpeedNonRecoverableHighCleared NOTIFICATION-TYPE 
STATUS current
-- ENTERPRISE petevts 
DESCRIPTION  
"Critical Cooling Device Under Speed problem (Lower non-recoverable, going high) Cleared" 

--#TYPE       "Cooling Device Event" 
--#SUMMARY    "Cooling Device Under Speed Warning (Lower non-recoverable, going high) Cleared" 
--#ARGUMENTS  {} 
--#SEVERITY   INFORMATIONAL 

::= { petevts 655749 }
 
-- Cooling Device speed decreased below Upper non-critical threshold Cleared 
trapCoolingDeviceOverSpeedWarningLowCleared NOTIFICATION-TYPE 
STATUS current
-- ENTERPRISE petevts 
DESCRIPTION  
"Cooling Device Over Speed Warning (Upper non-critical, going low) Cleared" 

--#TYPE       "Cooling Device Event" 
--#SUMMARY    "Cooling Device Over Speed Warning (Upper non-critical, going low) Cleared" 
--#ARGUMENTS  {} 
--#SEVERITY   INFORMATIONAL 

::= { petevts 655750 }
 
-- Cooling Device speed increased above upper non-critical threshold Cleared 
trapCoolingDeviceOverSpeedWarningHighCleared NOTIFICATION-TYPE 
STATUS current
-- ENTERPRISE petevts 
DESCRIPTION  
"Cooling Device Over Speed Warning (Upper non-critical, going high)Cleared" 

--#TYPE       "Cooling Device Event" 
--#SUMMARY    "Cooling Device Over Speed Warning (Upper non-critical, going high)Cleared" 
--#ARGUMENTS  {} 
--#SEVERITY   INFORMATIONAL 

::= { petevts 655751 }
 
-- Cooling Device speed decreased below Upper critical threshold Cleared 
trapCoolingDeviceOverSpeedCriticalLowCleared NOTIFICATION-TYPE 
STATUS current
-- ENTERPRISE petevts 
DESCRIPTION  
"Critical Cooling Device Over Speed problem (Upper critical, going low) Cleared" 

--#TYPE       "Cooling Device Event" 
--#SUMMARY    "Cooling Device Over Speed Warning (Upper critical, going low) Cleared" 
--#ARGUMENTS  {} 
--#SEVERITY   INFORMATIONAL 

::= { petevts 655752 }
 
 -- Cooling Device speed increased above Upper critical threshold Cleared 
trapCoolingDeviceOverSpeedCriticalHighCleared NOTIFICATION-TYPE 
STATUS current
-- ENTERPRISE petevts 
DESCRIPTION  
"Critical Cooling Device Over Speed problem (Upper critical, going high)Cleared" 

--#TYPE       "Cooling Device Event" 
--#SUMMARY    "Cooling Device Over Speed Warning (Upper critical, going high)Cleared" 
--#ARGUMENTS  {} 
--#SEVERITY   INFORMATIONAL 

::= { petevts 655753 }
 
 -- Cooling Device speed decreased below Upper non-recoverable threshold Cleared 
trapCoolingDeviceOverSpeedNonRecoverableLowCleared NOTIFICATION-TYPE 
STATUS current
-- ENTERPRISE petevts 
DESCRIPTION  
"Critical Cooling Device Over Speed problem (Upper non-recoverable, going low)Cleared" 

--#TYPE       "Cooling Device Event" 
--#SUMMARY    "Cooling Device Over Speed Warning (Upper non-recoverable, going low)Cleared" 
--#ARGUMENTS  {} 
--#SEVERITY   INFORMATIONAL 

::= { petevts 655754 }
 
 -- Cooling Device speed increased above Upper non-recoverable threshold Cleared 
trapCoolingDeviceOverSpeedNonRecoverableHighCleared NOTIFICATION-TYPE 
STATUS current
-- ENTERPRISE petevts 
DESCRIPTION  
"Critical Cooling Device Over Speed problem (Upper non-recoverable, going high) Cleared" 

--#TYPE       "Cooling Device Event" 
--#SUMMARY    "Cooling Device Under Speed Warning (Upper non-recoverable, going high) Cleared" 
--#ARGUMENTS  {} 
--#SEVERITY   INFORMATIONAL 

::= { petevts 655755 }
 
 -- Cooling Device Removed/Absent 
trapCoolingDeviceRemoved NOTIFICATION-TYPE 
STATUS current
-- ENTERPRISE petevts 
DESCRIPTION  
 "Cooling Device Removed/Absent" 

--#TYPE       "Cooling Device Event" 
--#SUMMARY    "Cooling Device Removed/Absent" 
--#ARGUMENTS  {} 
--#SEVERITY   CRITICAL 

::= { petevts 657408 }
 
  -- Cooling Device Inserted/Present 
trapCoolingDeviceInserted NOTIFICATION-TYPE 
STATUS current
-- ENTERPRISE petevts 
DESCRIPTION  
 "Cooling Device Inserted/Present" 

--#TYPE       "Cooling Device Event" 
--#SUMMARY    "Cooling Device Inserted/Present" 
--#ARGUMENTS  {} 
--#SEVERITY   INFORMATIONAL 

::= { petevts 657409 }
 
-- Cooling Device Full Redundancy  
trapCoolingDeviceFullRedundancy NOTIFICATION-TYPE 
STATUS current
-- ENTERPRISE petevts 
DESCRIPTION  
 "Cooling Device redundancy has returned to Normal" 

--#TYPE       "Cooling Device Event" 
--#SUMMARY    "Cooling Device redundancy has returned to Normal" 
--#ARGUMENTS  {} 
--#SEVERITY   INFORMATIONAL 

::= { petevts 658176 }

-- Cooling Device Redundancy lost  
trapCoolingDeviceRedundancyLost NOTIFICATION-TYPE 
STATUS current
-- ENTERPRISE petevts 
DESCRIPTION  
 "Cooling Device Redundancy has been Lost" 

--#TYPE       "Cooling Device Event" 
--#SUMMARY    "Cooling Device Redundancy has been Lost" 
--#ARGUMENTS  {} 
--#SEVERITY   CRITICAL 

::= { petevts 658177 }

-- Cooling Device Redundancy degraded 
trapCoolingDeviceRedundancyDegraded NOTIFICATION-TYPE 
STATUS current
-- ENTERPRISE petevts 
DESCRIPTION  
 "Cooling Device Redundancy is in a degraded state" 

--#TYPE       "Cooling Device Event" 
--#SUMMARY    "Cooling Device Redundancy is in a degraded state" 
--#ARGUMENTS  {} 
--#SEVERITY   WARNING 

::= { petevts 658178 }

-- ********************************************** 
-- *		Memory			* 
-- ********************************************** 

-- Memory Predictive Failure state has been cleared 
trapMemoryPredictiveFailureDeasserted NOTIFICATION-TYPE 
STATUS current
-- ENTERPRISE petevts 
DESCRIPTION  
 "Memory Predictive Failure state has been cleared" 

--#TYPE       "Memory Event" 
--#SUMMARY    "Memory Predictive Failure state has been cleared." 
--#ARGUMENTS  {} 
--#SEVERITY   INFORMATIONAL 

::= { petevts 787456 }
 
-- Memory Predictive Failure state has been asserted 
trapMemoryPredictiveFailureAsserted NOTIFICATION-TYPE 
STATUS current
-- ENTERPRISE petevts 
DESCRIPTION  
 "Memory Predictive Failure state has been asserted" 

--#TYPE       "Memory Event" 
--#SUMMARY    "Memory Predictive Failure has been asserted." 
--#ARGUMENTS  {} 
--#SEVERITY   CRITICAL 

::= { petevts 787457 }

-- Correctable ECC or other correctable memory error detected. 
trapMemoryCorrectableEccError NOTIFICATION-TYPE 
STATUS current
-- ENTERPRISE petevts 
DESCRIPTION 
 "Correctable ECC or other correctable memory error detected." 

--#TYPE       "Memory Event" 
--#SUMMARY    "Correctable ECC or other correctable memory error detected." 
--#ARGUMENTS  {} 
--#SEVERITY   INFORMATIONAL 

::= { petevts 814848 }
 
-- Uncorrectable ECC or other uncorrectable memory error detected 
trapMemoryUncorrectableEccError NOTIFICATION-TYPE 
STATUS current
-- ENTERPRISE petevts 
DESCRIPTION 
 "Uncorrectable ECC or other uncorrectable memory error detected." 

--#TYPE       "Memory Event" 
--#SUMMARY    "Uncorrectable ECC or other uncorrectable memory error detected." 
--#ARGUMENTS  {} 
--#SEVERITY   INFORMATIONAL 

::= { petevts 814849 }

 -- Parity error detected. 
trapMemoryParityError NOTIFICATION-TYPE 
STATUS current
-- ENTERPRISE petevts 
DESCRIPTION 
 "Parity error detected." 

--#TYPE       "Memory Event" 
--#SUMMARY    "Parity error detected." 
--#ARGUMENTS  {} 
--#SEVERITY   INFORMATIONAL 

::= { petevts 814850 }
 
-- Memory Scrub Failed 
trapMemoryScrubFailed NOTIFICATION-TYPE 
STATUS current
-- ENTERPRISE petevts 
DESCRIPTION 
 "Memory Scrub Failed" 

--#TYPE       "Memory Event" 
--#SUMMARY    "Memory Scrub Failed" 
--#ARGUMENTS  {} 
--#SEVERITY   INFORMATIONAL 

::= { petevts 814851 }
 
-- Memory Device Disabled 
trapMemoryDeviceDisabled NOTIFICATION-TYPE 
STATUS current
-- ENTERPRISE petevts 
DESCRIPTION 
 "Memory Device Disabled." 

--#TYPE       "Memory Event" 
--#SUMMARY    "Memory Device Disabled." 
--#ARGUMENTS  {} 
--#SEVERITY   INFORMATIONAL 

::= { petevts 814852 }
 
 -- Correctable ECC / other correctable memory error logging limit reached 
trapMemoryCorrectableECC NOTIFICATION-TYPE 
STATUS current
-- ENTERPRISE petevts 
DESCRIPTION 
 "Correctable ECC / other correctable memory error logging limit reached" 

--#TYPE       "Memory Event" 
--#SUMMARY    "Correctable ECC / other correctable memory error logging limit reached" 
--#ARGUMENTS  {} 
--#SEVERITY   INFORMATIONAL 

::= { petevts 814853 }
 
-- Memory Presence detected 
trapMemoryPresenceDetectedAssert NOTIFICATION-TYPE 
STATUS current
-- ENTERPRISE petevts 
DESCRIPTION 
 "Memory Presence detected." 

--#TYPE       "Memory Event" 
--#SUMMARY    "Memory Presence detected." 
--#ARGUMENTS  {} 
--#SEVERITY   INFORMATIONAL 

::= { petevts 814854 }
 
 -- Configuration Error 
trapMemoryConfigurationError NOTIFICATION-TYPE 
STATUS current
-- ENTERPRISE petevts 
DESCRIPTION 
 "Memory Configuration Error detected." 

--#TYPE       "Memory Event" 
--#SUMMARY    "Memory Configuration Error  detected." 
--#ARGUMENTS  {} 
--#SEVERITY   INFORMATIONAL 

::= { petevts 814855 }
 
-- Spare Unit of Memory detected 
trapMemorySpareUnit NOTIFICATION-TYPE 
STATUS current
-- ENTERPRISE petevts 
DESCRIPTION 
 "Spare Unit of Memory detected" 

--#TYPE       "Memory Event" 
--#SUMMARY    "Spare Unit of Memory detected" 
--#ARGUMENTS  {} 
--#SEVERITY   INFORMATIONAL 

::= { petevts 814856 }
 
-- Memory Automatically Throttled 
trapMemoryAutomaticallyThrottled NOTIFICATION-TYPE 
STATUS current
-- ENTERPRISE petevts 
DESCRIPTION 
 "Memory Automatically Throttled" 

--#TYPE       "Memory Event" 
--#SUMMARY    "Memory Automatically Throttled" 
--#ARGUMENTS  {} 
--#SEVERITY   INFORMATIONAL 

::= { petevts 814857 }
 
-- Critical Overtemperature 
trapMemoryCriticalOvertemperature NOTIFICATION-TYPE 
STATUS current
-- ENTERPRISE petevts 
DESCRIPTION 
 "Memory event - Critical Overtemperature" 

--#TYPE       "Memory Event" 
--#SUMMARY    "Memory event - Critical Overtemperature" 
--#ARGUMENTS  {} 
--#SEVERITY   INFORMATIONAL 

::= { petevts 814858 }
 
-- Correctable ECC or other correctable memory error cleared. 
trapMemoryCorrectableEccErrorCleared NOTIFICATION-TYPE 
STATUS current
-- ENTERPRISE petevts 
DESCRIPTION 
 "Correctable ECC or other correctable memory error cleared." 

--#TYPE       "Memory Event" 
--#SUMMARY    "Correctable ECC or other correctable memory error cleared." 
--#ARGUMENTS  {} 
--#SEVERITY   INFORMATIONAL 

::= { petevts 814976 }
 
-- Uncorrectable ECC or other uncorrectable memory error cleared 
trapMemoryUncorrectableEccErrorCleared NOTIFICATION-TYPE 
STATUS current
-- ENTERPRISE petevts 
DESCRIPTION 
 "Uncorrectable ECC or other uncorrectable memory error Cleared." 

--#TYPE       "Memory Event" 
--#SUMMARY    "Uncorrectable ECC or other uncorrectable memory error Cleared." 
--#ARGUMENTS  {} 
--#SEVERITY   INFORMATIONAL 

::= { petevts 814977 }
 
 -- Parity error Cleared. 
trapMemoryParityErrorCleared NOTIFICATION-TYPE 
STATUS current
-- ENTERPRISE petevts 
DESCRIPTION 
 "Parity error Cleared." 

--#TYPE       "Memory Event" 
--#SUMMARY    "Parity error Cleared." 
--#ARGUMENTS  {} 
--#SEVERITY   INFORMATIONAL 

::= { petevts 814978 }

-- Memory Scrub Failure Cleared 
trapMemoryScrubFailureCleared NOTIFICATION-TYPE 
STATUS current
-- ENTERPRISE petevts 
DESCRIPTION 
 "Memory Scrub Failure Cleared" 

--#TYPE       "Memory Event" 
--#SUMMARY    "Memory Scrub Failure Cleared" 
--#ARGUMENTS  {} 
--#SEVERITY   INFORMATIONAL 

::= { petevts 814979 }

-- Memory Device Enabled 
trapMemoryDeviceEnabled NOTIFICATION-TYPE 
STATUS current
-- ENTERPRISE petevts 
DESCRIPTION 
 "Memory Device Enabled." 

--#TYPE       "Memory Event" 
--#SUMMARY    "Memory Device Enabled." 
--#ARGUMENTS  {} 
--#SEVERITY   INFORMATIONAL 

::= { petevts 814980 }
 
 -- Correctable ECC / other correctable memory error logging limit reached Cleared 
trapMemoryCorrectableECCCleared NOTIFICATION-TYPE 
STATUS current
-- ENTERPRISE petevts 
DESCRIPTION 
 "Correctable ECC / other correctable memory error logging limit reached Cleared" 

--#TYPE       "Memory Event" 
--#SUMMARY    "Correctable ECC / other correctable memory error logging limit reached Cleared" 
--#ARGUMENTS  {} 
--#SEVERITY   INFORMATIONAL 

::= { petevts 814981 }

-- Memory Presence detected Deassert 
trapMemoryPresenceNotDetected NOTIFICATION-TYPE 
STATUS current
-- ENTERPRISE petevts 
DESCRIPTION 
 "Memory Presence Not detected" 

--#TYPE       "Memory Event" 
--#SUMMARY    "Memory Presence not detected" 
--#ARGUMENTS  {} 
--#SEVERITY   INFORMATIONAL 

::= { petevts 814982 }
 
 -- Configuration Error Cleared 
trapMemoryConfigurationErrorCleared NOTIFICATION-TYPE 
STATUS current
-- ENTERPRISE petevts 
DESCRIPTION 
 "Memory Configuration Error Cleared." 

--#TYPE       "Memory Event" 
--#SUMMARY    "Memory Configuration Error  Cleared." 
--#ARGUMENTS  {} 
--#SEVERITY   INFORMATIONAL 

::= { petevts 814983 }

-- Spare Unit of Memory detected Deassert 
trapMemorySpareUnitDeassert NOTIFICATION-TYPE 
STATUS current
-- ENTERPRISE petevts 
DESCRIPTION 
 "Spare Unit of Memory detected Deassert" 

--#TYPE       "Memory Event" 
--#SUMMARY    "Spare Unit of Memory detected Deassert" 
--#ARGUMENTS  {} 
--#SEVERITY   INFORMATIONAL 

::= { petevts 814984 }

-- Memory Automatically Throttled Cleared 
trapMemoryAutomaticallyThrottledCleared NOTIFICATION-TYPE 
STATUS current
-- ENTERPRISE petevts 
DESCRIPTION 
 "Memory Automatically Throttled Cleared" 

--#TYPE       "Memory Event" 
--#SUMMARY    "Memory Automatically Throttled Cleared" 
--#ARGUMENTS  {} 
--#SEVERITY   INFORMATIONAL 

::= { petevts 814985 }

-- Critical Overtemperature Cleared 
trapMemoryCriticalOvertemperatureCleared NOTIFICATION-TYPE 
STATUS current
-- ENTERPRISE petevts 
DESCRIPTION 
 "Memory event - Critical Overtemperature Cleared" 

--#TYPE       "Memory Event" 
--#SUMMARY    "Memory event - Critical Overtemperature Cleared"s 
--#ARGUMENTS  {} 
--#SEVERITY   INFORMATIONAL 

::= { petevts 814986 }

-- ********************************************** 
-- *		Drive Slot (Bay)			* 
-- ********************************************** 
-- Hard Disk Drive Fault Sensor event 
trapDriveSlotPredictiveFailureDeasserted NOTIFICATION-TYPE 
STATUS current
-- ENTERPRISE petevts 
DESCRIPTION  
 "This state indicates that a HDD Fault LED which was ON before is OFF now." 

--#TYPE       "Drive Slot Event" 
--#SUMMARY    "Hard Disk Drive Fault LED is OFF." 
--#ARGUMENTS  {} 
--#SEVERITY   INFORMATIONAL 

::= { petevts 852992 }

-- Hard Disk Drive Fault Sensor event 
trapDriveSlotPredictiveFailureAsserted NOTIFICATION-TYPE 
STATUS current
-- ENTERPRISE petevts 
DESCRIPTION  
 "A HDD Fault LED is ON." 

--#TYPE       "Drive Slot Event" 
--#SUMMARY    "Hard Disk Drive Fault LED is ON." 
--#ARGUMENTS  {} 
--#SEVERITY   MAJOR 

::= { petevts 852993 }


-- Hard Disk Drive Presence Sensor event 
trapDriveSlotDriveRemovedOrAbsent NOTIFICATION-TYPE 
STATUS current
-- ENTERPRISE petevts 
DESCRIPTION 
 "Hard Disk Drive is absent or has been removed." 

--#TYPE         "Drive Slot Event" 
--#SUMMARY      "Hard Disk Drive is absent or has been removed." 
--#ARGUMENTS    {} 
--#SEVERITY     INFORMATIONAL 

::= { petevts 880512 }
-- Change from 880384 to 880512 for Insert Alert Absent, Remove Alert Present 20141010<<>>
 
-- Hard Disk Drive Fault 
trapDriveSlotDriveFault NOTIFICATION-TYPE 
STATUS current
-- ENTERPRISE petevts 
DESCRIPTION 
 "Hard Disk Drive Fault" 

--#TYPE         "Drive Slot Event" 
--#SUMMARY      "Hard Disk Drive Fault" 
--#ARGUMENTS    {} 
--#SEVERITY     CRITICAL 

::= { petevts 880385 }

-- Hard Disk Drive Predictive Failure 
trapDriveSlotPredictiveFailure NOTIFICATION-TYPE 
STATUS current
-- ENTERPRISE petevts 
DESCRIPTION 
 "Hard Disk Drive Predictive Failure" 

--#TYPE         "Drive Slot Event" 
--#SUMMARY      "Hard Disk Drive Predictive Failure" 
--#ARGUMENTS    {} 
--#SEVERITY     INFORMATIONAL 

::= { petevts 880386 }

-- Hard Disk Drive Hot Spare (Ready to Remove) 
trapDriveSlotHotSpare NOTIFICATION-TYPE 
STATUS current
-- ENTERPRISE petevts 
DESCRIPTION 
  " Hard Disk Drive Hot Spare (Ready to remove) Asserted " 

--#TYPE         "Drive Slot Event" 
--#SUMMARY      "Hard Disk Drive Hot spare (Ready to Remove) " 
--#ARGUMENTS    {} 
--#SEVERITY     INFORMATIONAL 

::= { petevts 880387 }

-- Hard Disk Drive Consistency Check / Parity Check in progress 
trapDriveSlotConsistencyCheckInProgress NOTIFICATION-TYPE 
STATUS current
-- ENTERPRISE petevts 
DESCRIPTION 
 "Hard Disk Drive Consistency Check / Parity Check in progress" 

--#TYPE         "Drive Slot Event" 
--#SUMMARY      "Hard Disk Drive Consistency Check / Parity Check in progress" 
--#ARGUMENTS    {} 
--#SEVERITY     INFORMATIONAL 

::= { petevts 880388 }

-- Hard Disk Drive In Critical Array 
trapDriveSlotInCriticalArray NOTIFICATION-TYPE 
STATUS current
-- ENTERPRISE petevts 
DESCRIPTION 
 "Hard Disk Drive In Critical Array" 

--#TYPE         "Drive Slot Event" 
--#SUMMARY      "Hard Disk Drive In Critical Array" 
--#ARGUMENTS    {} 
--#SEVERITY     INFORMATIONAL 

::= { petevts 880389 }

-- Hard Disk Drive In Failed Array 
trapDriveSlotInFailedArray NOTIFICATION-TYPE 
STATUS current
-- ENTERPRISE petevts 
DESCRIPTION 
 "Hard Disk Drive In Failed Array" 

--#TYPE         "Drive Slot Event" 
--#SUMMARY      "Hard Disk Drive In Failed Array" 
--#ARGUMENTS    {} 
--#SEVERITY     CRITICAL 

::= { petevts 880390 }

-- Hard Disk Drive Rebuild/Remap in progress 
trapDriveSlotRebuildOrRemapInProgress NOTIFICATION-TYPE 
STATUS current
-- ENTERPRISE petevts 
DESCRIPTION 
 "Hard Disk Drive Rebuild/Remap in progress" 

--#TYPE         "Drive Slot Event" 
--#SUMMARY      "Hard Disk Drive Rebuild/Remap in progress" 
--#ARGUMENTS    {} 
--#SEVERITY     INFORMATIONAL 

::= { petevts 880391 }

-- Hard Disk Drive Rebuild/Remap Aborted 
trapDriveSlotRebuildOrRemapAborted NOTIFICATION-TYPE 
STATUS current
-- ENTERPRISE petevts 
DESCRIPTION 
 "Hard Disk Drive Rebuild/Remap Aborted" 

--#TYPE         "Drive Slot Event" 
--#SUMMARY      "Hard Disk Drive Rebuild/Remap Aborted" 
--#ARGUMENTS    {} 
--#SEVERITY     INFORMATIONAL 

::= { petevts 880392 }

-- Drive Presence Sensor event 
trapDriveSlotDriveInsertedOrPresent NOTIFICATION-TYPE 
STATUS current
-- ENTERPRISE petevts 
DESCRIPTION 
 "Hard Disk Drive is present or has been inserted." 

--#TYPE         "Drive Slot Event" 
--#SUMMARY      "Hard Disk Drive is present or has been inserted." 
--#ARGUMENTS    {} 
--#SEVERITY     INFORMATIONAL 


::= { petevts 880384 }
-- Change from 880512 to 880384 for Insert Alert Absent, Remove Alert Present 20141010<<>>

-- Hard Disk Drive Fault Cleared 
trapDriveSlotDriveFaultCleared NOTIFICATION-TYPE 
STATUS current
-- ENTERPRISE petevts 
DESCRIPTION 
 "Hard Disk Drive Fault Cleared" 

--#TYPE         "Drive Slot Event" 
--#SUMMARY      "Hard Disk Drive Fault Cleared" 
--#ARGUMENTS    {} 
--#SEVERITY     INFORMATIONAL 

::= { petevts 880513 }

-- Hard Disk Drive Predictive Failure Cleared 
trapDriveSlotPredictiveFailureCleared NOTIFICATION-TYPE 
STATUS current
-- ENTERPRISE petevts 
DESCRIPTION 
 "Hard Disk Drive Predictive Failure Cleared" 

--#TYPE         "Drive Slot Event" 
--#SUMMARY      "Hard Disk Drive Predictive Failure Cleared" 
--#ARGUMENTS    {} 
--#SEVERITY     INFORMATIONAL 

::= { petevts 880514 }

-- Hard Disk Drive Hot Spare 
trapDriveSlotHotSpareDeasserted NOTIFICATION-TYPE 
STATUS current
-- ENTERPRISE petevts 
DESCRIPTION 
 "Hard Disk Drive Hot Spare Deasserted" 

--#TYPE         "Drive Slot Event" 
--#SUMMARY      "Hard Disk Drive Hot spare" 
--#ARGUMENTS    {} 
--#SEVERITY     INFORMATIONAL 

::= { petevts 880515 }

-- Hard Disk Drive Consistency Check / Parity Check in progress Deasserted 
trapDriveSlotConsistencyCheckInProgressDeasserted NOTIFICATION-TYPE 
STATUS current
-- ENTERPRISE petevts 
DESCRIPTION 
 "Hard Disk Drive Consistency Check / Parity Check in progress Deasserted" 

--#TYPE         "Drive Slot Event" 
--#SUMMARY      "Hard Disk Drive Consistency Check / Parity Check in progress Deasserted" 
--#ARGUMENTS    {} 
--#SEVERITY     INFORMATIONAL 

::= { petevts 880516 }

-- Hard Disk Drive In Critical Array Deasserted 
trapDriveSlotInCriticalArrayDeasserted NOTIFICATION-TYPE 
STATUS current
-- ENTERPRISE petevts 
DESCRIPTION 
 "Hard Disk Drive In Critical Array Deasserted" 

--#TYPE         "Drive Slot Event" 
--#SUMMARY      "Hard Disk Drive In Critical Array Deasserted" 
--#ARGUMENTS    {} 
--#SEVERITY     INFORMATIONAL 

::= { petevts 880517 }

-- Hard Disk Drive In Failed Array Deasserted 
trapDriveSlotInFailedArrayDeasserted NOTIFICATION-TYPE 
STATUS current
-- ENTERPRISE petevts 
DESCRIPTION 
 "Hard Disk Drive In Failed Array Deasserted" 

--#TYPE         "Drive Slot Event" 
--#SUMMARY      "Hard Disk Drive In Failed Array Deasserted" 
--#ARGUMENTS    {} 
--#SEVERITY     CRITICAL 

::= { petevts 880518 }

-- Hard Disk Drive Rebuild/Remap in progress Deasserted 
trapDriveSlotRebuildOrRemapInProgressDeasserted NOTIFICATION-TYPE 
STATUS current
-- ENTERPRISE petevts 
DESCRIPTION 
 "Hard Disk Drive Rebuild/Remap in progress Deasserted(completed)" 

--#TYPE         "Drive Slot Event" 
--#SUMMARY      "Hard Disk Drive Rebuild/Remap in progress Deasserted(completed)" 
--#ARGUMENTS    {} 
--#SEVERITY     INFORMATIONAL 

::= { petevts 880519 }

-- Hard Disk Drive Rebuild/Remap Aborted Deasserted(completed) 
trapDriveSlotRebuildOrRemapAbortedDeasserted NOTIFICATION-TYPE 
STATUS current
-- ENTERPRISE petevts 
DESCRIPTION 
 "Hard Disk Drive Rebuild/Remap Aborted Deasserted" 

--#TYPE         "Drive Slot Event" 
--#SUMMARY      "Hard Disk Drive Rebuild/Remap Aborted Deasserted(completed)" 
--#ARGUMENTS    {} 
--#SEVERITY     INFORMATIONAL 

::= { petevts 880520 }

-- ********************************************** 
-- *		POST Memory Resize			* 
-- ********************************************** 

-- POST Memory Resize Failure Deasserted 
trapPOSTMemoryResizeFailureDeasserted NOTIFICATION-TYPE 
STATUS current
-- ENTERPRISE petevts 
DESCRIPTION  
 "POST Memory Resize Failure Deasserted" 

--#TYPE       "POST Memory Resize Event" 
--#SUMMARY    "POST Memory Resize Failure Deasserted" 
--#ARGUMENTS  {} 
--#SEVERITY   INFORMATIONAL 

::= { petevts 918528 }

-- POST Memory Resize Failure Asserted 
trapPOSTMemoryResizeFailureAsserted NOTIFICATION-TYPE 
STATUS current
-- ENTERPRISE petevts 
DESCRIPTION  
 "POST Memory Resize Failure Asserted" 

--#TYPE       "POST Memory Resize Event" 
--#SUMMARY    "POST Memory Resize Failure Asserted" 
--#ARGUMENTS  {} 
--#SEVERITY   MAJOR 

::= { petevts 918529 }

-- ********************************************** 
-- *		System Firmware Progress			* 
-- ********************************************** 

-- Power On Self Test (POST) code error 
trapBIOSPOSTCodeError NOTIFICATION-TYPE 
STATUS current
-- ENTERPRISE petevts 
DESCRIPTION  
 "System Firmware Progress: BIOS POST code error" 

--#TYPE       "System Firmware Progress Event" 
--#SUMMARY    "System Firmware Progress: BIOS POST code error" 
--#ARGUMENTS  {} 
--#SEVERITY   CRITICAL 

::= { petevts 1011456 }

-- System Firmware Hang 
trapSystemFirmwareHang NOTIFICATION-TYPE 
STATUS current
-- ENTERPRISE petevts 
DESCRIPTION  
 "System Firmware Hang" 

--#TYPE       "System Firmware Progress Event" 
--#SUMMARY    "System Firmware Hang" 
--#ARGUMENTS  {} 
--#SEVERITY   CRITICAL 

::= { petevts 1011457 }

-- System Firmware Progress 
trapSystemFirmwareProgress NOTIFICATION-TYPE 
STATUS current
-- ENTERPRISE petevts 
DESCRIPTION  
 "System Firmware Progress" 

--#TYPE       "System Firmware Progress Event" 
--#SUMMARY    "System Firmware Progress" 
--#ARGUMENTS  {} 
--#SEVERITY   INFORMATIONAL 

::= { petevts 1011458 }

-- Power On Self Test (POST) code error Cleared 
trapBIOSPOSTCodeErrorCleared NOTIFICATION-TYPE 
STATUS current
-- ENTERPRISE petevts 
DESCRIPTION  
 "System Firmware Progress: BIOS POST code error Cleared" 

--#TYPE       "System Firmware Progress Event" 
--#SUMMARY    "System Firmware Progress: BIOS POST code error Cleared" 
--#ARGUMENTS  {} 
--#SEVERITY   INFORMATIONAL 

::= { petevts 1011584 }

-- System Firmware Hang Cleared 
trapSystemFirmwareHangCleared NOTIFICATION-TYPE 
STATUS current
-- ENTERPRISE petevts 
DESCRIPTION  
 "System Firmware Hang Cleared" 

--#TYPE       "System Firmware Progress Event" 
--#SUMMARY    "System Firmware Hang Cleared" 
--#ARGUMENTS  {} 
--#SEVERITY   INFORMATIONAL 

::= { petevts 1011585 }

-- System Firmware Progress Completed  
trapSystemFirmwareProgressCompleted NOTIFICATION-TYPE 
STATUS current
-- ENTERPRISE petevts 
DESCRIPTION  
 "System Firmware Progress Completed " 

--#TYPE       "System Firmware Progress Event" 
--#SUMMARY    "System Firmware Progress Completed " 
--#ARGUMENTS  {} 
--#SEVERITY   INFORMATIONAL 

::= { petevts 1011586 }

-- ********************************************** 
-- *		Event Logging Disabled			* 
-- ********************************************** 

-- Correctable Memory Error Logging Disabled 
trapCorrectableMemoryErrorLoggingDisabled NOTIFICATION-TYPE 
STATUS current
-- ENTERPRISE petevts 
DESCRIPTION  
 "Correctable Memory Error Logging Disabled" 

--#TYPE       "System Event Log" 
--#SUMMARY    "Correctable Memory Error Logging Disabled" 
--#ARGUMENTS  {} 
--#SEVERITY   INFORMATIONAL 

::= { petevts 1076992 }

-- Event Type Logging Disabled. 
trapEventTypeLoggingDisabled NOTIFICATION-TYPE 
STATUS current
-- ENTERPRISE petevts 
DESCRIPTION  
 "Event Type Logging Disabled" 

--#TYPE       "System Event Log" 
--#SUMMARY    "Event Type Logging Disabled." 
--#ARGUMENTS  {} 
--#SEVERITY   INFORMATIONAL 

::= { petevts 1076993 }

-- SEL Area Reset/Cleared 
trapSELAreaResetOrCleared NOTIFICATION-TYPE 
STATUS current
-- ENTERPRISE petevts 
DESCRIPTION  
 "SEL Area Reset/Cleared" 

--#TYPE       "System Event Log" 
--#SUMMARY    "SEL Area Reset/Cleared" 
--#ARGUMENTS  {} 
--#SEVERITY   INFORMATIONAL 

::= { petevts 1076994 }

-- All Event Logging Disabled 
trapEventLoggingDisabled NOTIFICATION-TYPE 
STATUS current
-- ENTERPRISE petevts 
DESCRIPTION  
 "System Event Logging Disabled" 

--#TYPE       "System Event Log" 
--#SUMMARY    "System Event Logging Disabled" 
--#ARGUMENTS  {} 
--#SEVERITY   CRITICAL 

::= { petevts 1076995 }

-- SEL Full 
trapSelFull NOTIFICATION-TYPE 
STATUS current
-- ENTERPRISE petevts 
DESCRIPTION 
 "SEL Full." 

--#TYPE       "System Event Log" 
--#SUMMARY    "SEL Full." 
--#ARGUMENTS  {} 
--#SEVERITY   INFORMATIONAL 

::= { petevts 1076996 }

 -- SEL Almost Full 
trapSelAlmostFull NOTIFICATION-TYPE 
STATUS current
-- ENTERPRISE petevts 
DESCRIPTION 
 "SEL Almost Full." 

--#TYPE       "System Event Log" 
--#SUMMARY    "SEL Almost Full." 
--#ARGUMENTS  {} 
--#SEVERITY   INFORMATIONAL 

::= { petevts 1076997 }

-- Correctable Machine Check Error Logging Disabled 
trapCorrectableMachineCheckErrorLoggingDisabled NOTIFICATION-TYPE 
STATUS current
-- ENTERPRISE petevts 
DESCRIPTION 
 "Correctable Machine Check Error Logging Disabled" 

--#TYPE       "System Event Log" 
--#SUMMARY    "Correctable Machine Check Error Logging Disabled" 
--#ARGUMENTS  {} 
--#SEVERITY   INFORMATIONAL 

::= { petevts 1076998  }

-- Correctable Memory Error Logging Enabled 
trapCorrectableMemoryErrorLoggingEnabled NOTIFICATION-TYPE 
STATUS current
-- ENTERPRISE petevts 
DESCRIPTION  
 "Correctable Memory Error Logging Enabled" 

--#TYPE       "System Event Log" 
--#SUMMARY    "Correctable Memory Error Logging Enabled" 
--#ARGUMENTS  {} 
--#SEVERITY   INFORMATIONAL 

::= { petevts 1077120 }

-- Event Type Logging Enabled. 
trapEventTypeLoggingEnabled NOTIFICATION-TYPE 
STATUS current
-- ENTERPRISE petevts 
DESCRIPTION  
 "Event Type Logging Enabled" 

--#TYPE       "System Event Log" 
--#SUMMARY    "Event Type Logging Enabled." 
--#ARGUMENTS  {} 
--#SEVERITY   INFORMATIONAL 

::= { petevts 1077121 }

-- SEL Area Reset/Cleared Event Deasserted 
trapSELAreaResetOrClearedEventDeassert NOTIFICATION-TYPE 
STATUS current
-- ENTERPRISE petevts 
DESCRIPTION  
 "SEL Area Reset/Cleared" 

--#TYPE       "System Event Log" 
--#SUMMARY    "SEL Area Reset/Cleared Event Deasserted" 
--#ARGUMENTS  {} 
--#SEVERITY   INFORMATIONAL 

::= { petevts 1077122 }

-- All Event Logging Enabled 
trapEventLoggingEnabled NOTIFICATION-TYPE 
STATUS current
-- ENTERPRISE petevts 
DESCRIPTION  
 "System Event Logging Enabled" 

--#TYPE       "System Event Log" 
--#SUMMARY    "System Event Logging Enabled" 
--#ARGUMENTS  {} 
--#SEVERITY   INFORMATIONAL 

::= { petevts 1077123 }

-- SEL Full Event Cleared 
trapSelFullEventCleared NOTIFICATION-TYPE 
STATUS current
-- ENTERPRISE petevts 
DESCRIPTION 
 "SEL Full Event Cleared" 

--#TYPE       "System Event Log" 
--#SUMMARY    "SEL Full Event Cleared" 
--#ARGUMENTS  {} 
--#SEVERITY   INFORMATIONAL 

::= { petevts 1077124 }

 -- SEL Almost Full Event Cleared 
trapSelAlmostFullEventCleared NOTIFICATION-TYPE 
STATUS current
-- ENTERPRISE petevts 
DESCRIPTION 
 "SEL Almost Full Event Cleared" 

--#TYPE       "System Event Log" 
--#SUMMARY    "SEL Almost Full Event Cleared" 
--#ARGUMENTS  {} 
--#SEVERITY   INFORMATIONAL 

::= { petevts 1077125 }

-- Correctable Machine Check Error Logging Enabled 
trapCorrectableMachineCheckErrorLoggingEnabled NOTIFICATION-TYPE 
STATUS current
-- ENTERPRISE petevts 
DESCRIPTION 
 "Correctable Machine Check Error Logging Enabled" 

--#TYPE       "System Event Log" 
--#SUMMARY    "Correctable Machine Check Error Logging Enabled" 
--#ARGUMENTS  {} 
--#SEVERITY   INFORMATIONAL 

::= { petevts 1077126 }

-- ********************************************** 
-- *		WatchDog1			* 
-- ********************************************** 
-- BIOS Watchdog Reset 
trapBIOSWatchdogReset NOTIFICATION-TYPE 
STATUS current
-- ENTERPRISE petevts 
DESCRIPTION 
 "BIOS Watchdog Reset" 

--#TYPE       "Watchdog Event" 
--#SUMMARY    "BIOS Watchdog Reset" 
--#ARGUMENTS  {} 
--#SEVERITY   INFORMATIONAL 

::= { petevts 1142528 }

-- OS Watchdog Reset 
trapOSWatchdogReset NOTIFICATION-TYPE 
STATUS current
-- ENTERPRISE petevts 
DESCRIPTION 
 "OS Watchdog Reset" 

--#TYPE       "Watchdog Event" 
--#SUMMARY    "OS Watchdog Reset" 
--#ARGUMENTS  {} 
--#SEVERITY   INFORMATIONAL 

::= { petevts 1142529 }

-- OS Watchdog Shut Down 
trapOSWatchdogShutDown NOTIFICATION-TYPE 
STATUS current
-- ENTERPRISE petevts 
DESCRIPTION 
 "OS Watchdog Shut Down" 

--#TYPE       "Watchdog Event" 
--#SUMMARY    "OS Watchdog Shut Down" 
--#ARGUMENTS  {} 
--#SEVERITY   INFORMATIONAL 

::= { petevts 1142530 }

-- OS Watchdog Power Down 
trapOSWatchdogPowerDown NOTIFICATION-TYPE 
STATUS current
-- ENTERPRISE petevts 
DESCRIPTION 
 "OS Watchdog Power Down" 

--#TYPE       "Watchdog Event" 
--#SUMMARY    "OS Watchdog Power Down" 
--#ARGUMENTS  {} 
--#SEVERITY   INFORMATIONAL 

::= { petevts 1142531 }

-- OS Watchdog Power Cycle 
trapOSWatchdogPowerCycle NOTIFICATION-TYPE 
STATUS current
-- ENTERPRISE petevts 
DESCRIPTION 
 "OS Watchdog Power Cycle" 

--#TYPE       "Watchdog Event" 
--#SUMMARY    "OS Watchdog Power Cycle" 
--#ARGUMENTS  {} 
--#SEVERITY   INFORMATIONAL 

::= { petevts 1142532 }

-- OS Watchdog NMI / Diagnostic Interrupt 
trapOSWatchdogNMIOrDiagnosticInterrupt NOTIFICATION-TYPE 
STATUS current
-- ENTERPRISE petevts 
DESCRIPTION 
 "OS Watchdog NMI / Diagnostic Interrupt" 

--#TYPE       "Watchdog Event" 
--#SUMMARY    "OS Watchdog NMI / Diagnostic Interrupt" 
--#ARGUMENTS  {} 
--#SEVERITY   INFORMATIONAL 

::= { petevts 1142533 }

-- OS Watchdog Expired, status only 
trapOSWatchdogExpired NOTIFICATION-TYPE 
STATUS current
-- ENTERPRISE petevts 
DESCRIPTION 
 "OS Watchdog Expired, status only" 

--#TYPE       "Watchdog Event" 
--#SUMMARY    "OS Watchdog Expired, status only" 
--#ARGUMENTS  {} 
--#SEVERITY   INFORMATIONAL 

::= { petevts 1142534 }

-- OS Watchdog pre-timeout Interrupt, non-NMI 
trapOSWatchdogPreTimeoutInterrupt NOTIFICATION-TYPE 
STATUS current
-- ENTERPRISE petevts 
DESCRIPTION 
 "OS Watchdog pre-timeout Interrupt, non-NMI" 

--#TYPE       "Watchdog Event" 
--#SUMMARY    "OS Watchdog pre-timeout Interrupt, non-NMI" 
--#ARGUMENTS  {} 
--#SEVERITY   INFORMATIONAL 

::= { petevts 1142535 }

-- BIOS Watchdog Reset Deasserted 
trapBIOSWatchdogResetDeasserted NOTIFICATION-TYPE 
STATUS current
-- ENTERPRISE petevts 
DESCRIPTION 
 "BIOS Watchdog Reset Deasserted" 

--#TYPE       "Watchdog Event" 
--#SUMMARY    "BIOS Watchdog Reset Deasserted" 
--#ARGUMENTS  {} 
--#SEVERITY   INFORMATIONAL 

::= { petevts 1142656 }

-- OS Watchdog Reset Deasserted 
trapOSWatchdogResetDeasserted NOTIFICATION-TYPE 
STATUS current
-- ENTERPRISE petevts 
DESCRIPTION 
 "OS Watchdog Reset Deasserted" 

--#TYPE       "Watchdog Event" 
--#SUMMARY    "OS Watchdog Reset Deasserted" 
--#ARGUMENTS  {} 
--#SEVERITY   INFORMATIONAL 

::= { petevts 1142657 }

-- OS Watchdog Shut Down Deasserted 
trapOSWatchdogShutDownDeasserted NOTIFICATION-TYPE 
STATUS current
-- ENTERPRISE petevts 
DESCRIPTION 
 "OS Watchdog Shut Down Deasserted" 

--#TYPE       "Watchdog Event" 
--#SUMMARY    "OS Watchdog Shut Down Deasserted" 
--#ARGUMENTS  {} 
--#SEVERITY   INFORMATIONAL 

::= { petevts 1142658 }

-- OS Watchdog Power Down Deasserted 
trapOSWatchdogPowerDownDeasserted NOTIFICATION-TYPE 
STATUS current
-- ENTERPRISE petevts 
DESCRIPTION 
 "OS Watchdog Power Down Deasserted" 

--#TYPE       "Watchdog Event" 
--#SUMMARY    "OS Watchdog Power Down Deasserted" 
--#ARGUMENTS  {} 
--#SEVERITY   INFORMATIONAL 

::= { petevts 1142659 }

-- OS Watchdog Power Cycle Deasserted 
trapOSWatchdogPowerCycleDeasserted NOTIFICATION-TYPE 
STATUS current
-- ENTERPRISE petevts 
DESCRIPTION 
 "OS Watchdog Power Cycle Deasserted" 

--#TYPE       "Watchdog Event" 
--#SUMMARY    "OS Watchdog Power Cycle Deasserted" 
--#ARGUMENTS  {} 
--#SEVERITY   INFORMATIONAL 

::= { petevts 1142660 }

-- OS Watchdog NMI / Diagnostic Interrupt Cleared 
trapOSWatchdogNMIOrDiagnosticInterruptCleared NOTIFICATION-TYPE 
STATUS current
-- ENTERPRISE petevts 
DESCRIPTION 
 "OS Watchdog NMI / Diagnostic Interrupt Cleared" 

--#TYPE       "Watchdog Event" 
--#SUMMARY    "OS Watchdog NMI / Diagnostic Interrupt Cleared" 
--#ARGUMENTS  {} 
--#SEVERITY   INFORMATIONAL 

::= { petevts 1142661 }

-- OS Watchdog Expired, status only Event Cleared 
trapOSWatchdogExpiredEventCleared NOTIFICATION-TYPE 
STATUS current
-- ENTERPRISE petevts 
DESCRIPTION 
 "OS Watchdog Expired, status only Event Cleared" 

--#TYPE       "Watchdog Event" 
--#SUMMARY    "OS Watchdog Expired, status only Event Cleared" 
--#ARGUMENTS  {} 
--#SEVERITY   INFORMATIONAL 

::= { petevts 1142662 }

-- OS Watchdog pre-timeout Interrupt, (non-NMI) Cleared 
trapOSWatchdogPreTimeoutInterruptCleared NOTIFICATION-TYPE 
STATUS current
-- ENTERPRISE petevts 
DESCRIPTION 
 "OS Watchdog pre-timeout Interrupt Cleared" 

--#TYPE       "Watchdog Event" 
--#SUMMARY    "OS Watchdog pre-timeout Interrupt Cleared" 
--#ARGUMENTS  {} 
--#SEVERITY   INFORMATIONAL 

::= { petevts 1142663  }

-- ********************************************** 
-- *		System Event			* 
-- ********************************************** 

-- System Reconfigured 
trapSystemReconfigured NOTIFICATION-TYPE 
STATUS current
-- ENTERPRISE petevts 
DESCRIPTION 
 "System Reconfigured" 

--#TYPE       "System Event" 
--#SUMMARY    "System Reconfigured" 
--#ARGUMENTS  {} 
--#SEVERITY   INFORMATIONAL 

::= { petevts 1208064 }

-- OEM System Boot Event 
trapOEMSystemBootEvent NOTIFICATION-TYPE 
STATUS current
-- ENTERPRISE petevts 
DESCRIPTION 
 "OEM System Boot Event" 

--#TYPE       "System Event" 
--#SUMMARY    "OEM System Boot Event" 
--#ARGUMENTS  {} 
--#SEVERITY   WARNING 

::= { petevts 1208065 }

-- Undetermined system hardware failure 
trapUndeterminedSystemHardwareFailure NOTIFICATION-TYPE 
STATUS current
-- ENTERPRISE petevts 
DESCRIPTION 
 "Undetermined system hardware failure" 

--#TYPE       "System Event" 
--#SUMMARY    "Undetermined system hardware failure" 
--#ARGUMENTS  {} 
--#SEVERITY   CRITICAL 

::= { petevts 1208066 }

-- SEL Entry added to Auxiliary Log 
trapEntryAddedToAuxiliaryLog NOTIFICATION-TYPE 
STATUS current
-- ENTERPRISE petevts 
DESCRIPTION 
 "SEL Entry added to Auxiliary Log" 

--#TYPE       "System Event" 
--#SUMMARY    "SEL Entry added to Auxiliary Log" 
--#ARGUMENTS  {} 
--#SEVERITY   INFORMATIONAL 

::= { petevts 1208067 }

-- PEF Action 
trapPEFAction NOTIFICATION-TYPE 
STATUS current
-- ENTERPRISE petevts 
DESCRIPTION 
 "PEF Action is about to be taken. Event filters have been matched." 

--#TYPE       "System Event" 
--#SUMMARY    "PEF Action is about to be taken. Event filters have been matched." 
--#ARGUMENTS  {} 
--#SEVERITY   INFORMATIONAL 

::= { petevts 1208068 }

-- Timestamp Clock Synch 
trapTimestampClockSynch NOTIFICATION-TYPE 
STATUS current
-- ENTERPRISE petevts 
DESCRIPTION 
 "Timestamp Clock Synch" 

--#TYPE       "System Event" 
--#SUMMARY    "Timestamp Clock Synch" 
--#ARGUMENTS  {} 
--#SEVERITY   INFORMATIONAL 

::= { petevts 1208069  }

-- System Reconfigured Event Cleared 
trapSystemReconfiguredDeassert NOTIFICATION-TYPE 
STATUS current
-- ENTERPRISE petevts 
DESCRIPTION 
 "System Reconfigured Event Cleared" 

--#TYPE       "System Event" 
--#SUMMARY    "System Reconfigured Event Cleared" 
--#ARGUMENTS  {} 
--#SEVERITY   INFORMATIONAL 

::= { petevts 1208192 }

-- OEM System Boot Event Cleared 
trapOEMSystemBootEventCleared NOTIFICATION-TYPE 
STATUS current
-- ENTERPRISE petevts 
DESCRIPTION 
 "OEM System Boot Event Cleared" 

--#TYPE       "System Event" 
--#SUMMARY    "OEM System Boot Event Cleared" 
--#ARGUMENTS  {} 
--#SEVERITY   INFORMATIONAL 

::= { petevts 1208193 }

-- Undetermined system hardware failure Cleared 
trapUndeterminedSystemHardwareFailureCleared NOTIFICATION-TYPE 
STATUS current
-- ENTERPRISE petevts 
DESCRIPTION 
 "Undetermined system hardware failure Cleared" 

--#TYPE       "System Event" 
--#SUMMARY    "Undetermined system hardware failure Cleared" 
--#ARGUMENTS  {} 
--#SEVERITY   CRITICAL 

::= { petevts 1208194 }

-- SEL Entry added to Auxiliary Log Deasserted 
trapEntryAddedToAuxiliaryLogDeassert NOTIFICATION-TYPE 
STATUS current
-- ENTERPRISE petevts 
DESCRIPTION 
 "SEL Entry added to Auxiliary Log Deasserted" 

--#TYPE       "System Event" 
--#SUMMARY    "SEL Entry added to Auxiliary Log Deasserted" 
--#ARGUMENTS  {} 
--#SEVERITY   INFORMATIONAL 

::= { petevts 1208195 }

-- PEF Action Event Deasserted 
trapPEFActionEventDeassert NOTIFICATION-TYPE 
STATUS current
-- ENTERPRISE petevts 
DESCRIPTION 
 "PEF Action Event Deasserted" 

--#TYPE       "System Event" 
--#SUMMARY    "PEF Action Event Deasserted" 
--#ARGUMENTS  {} 
--#SEVERITY   INFORMATIONAL 

::= { petevts 1208196 }

-- Timestamp Clock Synch Event Deasserted 
trapTimestampClockSynchEventDeassert NOTIFICATION-TYPE 
STATUS current
-- ENTERPRISE petevts 
DESCRIPTION 
 "Timestamp Clock Synch Event Deasserted" 

--#TYPE       "System Event" 
--#SUMMARY    "Timestamp Clock Synch Event Deasserted" 
--#ARGUMENTS  {} 
--#SEVERITY   INFORMATIONAL 

::= { petevts 1208197  }
  
-- ********************************************** 
-- *		Critical Interrupt			* 
-- ********************************************** 

-- Front Panel NMI / Diagnostic Interrupt 
trapCriticalInterruptFrontPanelNMI NOTIFICATION-TYPE 
STATUS current
-- ENTERPRISE petevts 
DESCRIPTION  
 "Front Panel NMI / Diagnostic Interrupt" 

--#TYPE       "Critical Interrupts Event" 
--#SUMMARY    "Front Panel NMI / Diagnostic Interrupt" 
--#ARGUMENTS  {} 
--#SEVERITY   CRITICAL 

::= { petevts 1273600 }

-- Critical Interrupt, Bus timeout error 
trapCriticalInterruptBusTimeout NOTIFICATION-TYPE 
STATUS current
-- ENTERPRISE petevts 
DESCRIPTION  
 "Critical Interrupt, Bus Timeout error" 

--#TYPE       "Critical Interrupts Event" 
--#SUMMARY    "Critical Interrupt, Bus Timeout error" 
--#ARGUMENTS  {} 
--#SEVERITY   CRITICAL 

::= { petevts 1273601 }

-- Critical Interrupt, IO Channel Non-Maskable Interrupt 
trapCriticalInterruptIOChannelNMI NOTIFICATION-TYPE 
STATUS current
-- ENTERPRISE petevts 
DESCRIPTION  
 "Critical Interrupt, IO Channel check NMI error" 

--#TYPE       "Critical Interrupts Event" 
--#SUMMARY    "Critical Interrupt, IO Channel check NMI error" 
--#ARGUMENTS  {} 
--#SEVERITY   CRITICAL 

::= { petevts 1273602 }

-- Critical Interrupt, Software Non-Maskable Interrupt error 
trapCriticalInterruptSoftwareNMI NOTIFICATION-TYPE 
STATUS current
-- ENTERPRISE petevts 
DESCRIPTION  
 "Critical Interrupt, software NMI error" 

--#TYPE       "Critical Interrupts Event" 
--#SUMMARY    "Critical Interrupt, software NMI error" 
--#ARGUMENTS  {} 
--#SEVERITY   CRITICAL 

::= { petevts 1273603 }

-- Non special-cycle parity errors 
trapCriticalInterruptPCIPERR NOTIFICATION-TYPE 
STATUS current
-- ENTERPRISE petevts 
DESCRIPTION  
 "Critical Interrupt, PCI PERR parity error" 

--#TYPE       "Critical Interrupts Event" 
--#SUMMARY    "Critical Interrupt, PCI PERR parity error" 
--#ARGUMENTS  {} 
--#SEVERITY   CRITICAL 

::= { petevts 1273604 }

-- Special-cycle parity errors 
trapCriticalInterruptPCISERR NOTIFICATION-TYPE 
STATUS current
-- ENTERPRISE petevts 
DESCRIPTION  
 "Critical Interrupt, PCI SERR parity error" 

--#TYPE       "Critical Interrupts Event" 
--#SUMMARY    "Critical Interrupt, PCI SERR parity error" 
--#ARGUMENTS  {} 
--#SEVERITY   CRITICAL 

::= { petevts 1273605 }

-- EISA Fail Safe Timeout 
trapCriticalInterruptEISAFailSafeTimeout NOTIFICATION-TYPE 
STATUS current
-- ENTERPRISE petevts 
DESCRIPTION  
 "Critical Interrupt, EISA Fail Safe Timeout" 

--#TYPE       "Critical Interrupts Event" 
--#SUMMARY    "Critical Interrupt, EISA Fail Safe Timeout" 
--#ARGUMENTS  {} 
--#SEVERITY   CRITICAL 

::= { petevts 1273606 }

-- Bus Correctable Error 
trapCriticalInterruptBusCorrectableError NOTIFICATION-TYPE 
STATUS current
-- ENTERPRISE petevts 
DESCRIPTION  
 "Critical Interrupt, Bus Correctable Error" 

--#TYPE       "Critical Interrupts Event" 
--#SUMMARY    "Critical Interrupt, Bus Correctable Error" 
--#ARGUMENTS  {} 
--#SEVERITY   CRITICAL 

::= { petevts 1273607 }

-- Bus uncorrectable error 
trapCriticalInterruptBusUncorrect NOTIFICATION-TYPE 
STATUS current
-- ENTERPRISE petevts 
DESCRIPTION  
 "Critical Interrupt, Bus Uncorrectable error" 

--#TYPE       "Critical Interrupts Event" 
--#SUMMARY    "Critical Interrupt, Bus Uncorrectable error" 
--#ARGUMENTS  {} 
--#SEVERITY   CRITICAL 

::= { petevts 1273608 }

-- Fatal non-maskable interrupt (NMI) 
trapCriticalInterruptFatalNMI NOTIFICATION-TYPE 
STATUS current
-- ENTERPRISE petevts 
DESCRIPTION  
 "Critical Interrupt, Fatal NMI error" 

--#TYPE       "Critical Interrupts Event" 
--#SUMMARY    "Critical Interrupt, Fatal NMI error" 
--#ARGUMENTS  {} 
--#SEVERITY   CRITICAL 

::= { petevts 1273609 }

-- Bus Fatal Error 
trapCriticalInterruptFatalBusError NOTIFICATION-TYPE 
STATUS current
-- ENTERPRISE petevts 
DESCRIPTION  
 "Critical Interrupt, Bus Fatal Error" 

--#TYPE       "Critical Interrupts Event" 
--#SUMMARY    "Critical Interrupt, Bus Fatal Error" 
--#ARGUMENTS  {} 
--#SEVERITY   CRITICAL 

::= { petevts 1273610 }

-- Bus Degraded (bus operating in a degraded performance state) 
trapCriticalInterruptBusDegraded NOTIFICATION-TYPE 
STATUS current
-- ENTERPRISE petevts 
DESCRIPTION  
 "Critical Interrupt, Bus Degraded (bus operating in a degraded performance state)" 

--#TYPE       "Critical Interrupts Event" 
--#SUMMARY    "Critical Interrupt, Bus Degraded (bus operating in a degraded performance state)" 
--#ARGUMENTS  {} 
--#SEVERITY   CRITICAL 

::= { petevts 1273611 }

-- Front Panel NMI / Diagnostic Interrupt Cleared 
trapCriticalInterruptFrontPanelNMICleared NOTIFICATION-TYPE 
STATUS current
-- ENTERPRISE petevts 
DESCRIPTION  
 "Front Panel NMI / Diagnostic Interrupt Cleared" 

--#TYPE       "Critical Interrupts Event" 
--#SUMMARY    "Front Panel NMI / Diagnostic Interrupt Cleared" 
--#ARGUMENTS  {} 
--#SEVERITY   INFORMATIONAL 

::= { petevts 1273728 }

-- Critical Interrupt, Bus timeout error Cleared 
trapCriticalInterruptBusTimeoutCleared NOTIFICATION-TYPE 
STATUS current
-- ENTERPRISE petevts 
DESCRIPTION  
 "Critical Interrupt, Bus Timeout error Cleared"  

--#TYPE       "Critical Interrupts Event" 
--#SUMMARY    "Critical Interrupt, Bus Timeout error Cleared" 
--#ARGUMENTS  {} 
--#SEVERITY   INFORMATIONAL 

::= { petevts 1273729 }

-- Critical Interrupt, IO Channel Non-Maskable Interrupt Cleared 
trapCriticalInterruptIOChannelNMICleared NOTIFICATION-TYPE 
STATUS current
-- ENTERPRISE petevts 
DESCRIPTION  
 "Critical Interrupt, IO Channel check NMI error Cleared" 

--#TYPE       "Critical Interrupts Event" 
--#SUMMARY    "Critical Interrupt, IO Channel check NMI error Cleared" 
--#ARGUMENTS  {} 
--#SEVERITY   INFORMATIONAL 

::= { petevts 1273730 }

-- Critical Interrupt, Software Non-Maskable Interrupt error Cleared 
trapCriticalInterruptSoftwareNMICleared NOTIFICATION-TYPE 
STATUS current
-- ENTERPRISE petevts 
DESCRIPTION  
 "Critical Interrupt, software NMI error Cleared" 

--#TYPE       "Critical Interrupts Event" 
--#SUMMARY    "Critical Interrupt, software NMI error Cleared" 
--#ARGUMENTS  {} 
--#SEVERITY   INFORMATIONAL 

::= { petevts 1273731 }

-- Non special-cycle parity errors Cleared 
trapCriticalInterruptPCIPERRCleared NOTIFICATION-TYPE 
STATUS current
-- ENTERPRISE petevts 
DESCRIPTION  
 "Critical Interrupt, PCI PERR parity error Cleared" 

--#TYPE       "Critical Interrupts Event" 
--#SUMMARY    "Critical Interrupt, PCI PERR parity error Cleared" 
--#ARGUMENTS  {} 
--#SEVERITY   INFORMATIONAL 

::= { petevts 1273732 }

-- Special-cycle parity errors Cleared 
trapCriticalInterruptPCISERRCleared NOTIFICATION-TYPE 
STATUS current
-- ENTERPRISE petevts 
DESCRIPTION  
 "Critical Interrupt, PCI SERR parity error Cleared" 

--#TYPE       "Critical Interrupts Event" 
--#SUMMARY    "Critical Interrupt, PCI SERR parity error Cleared" 
--#ARGUMENTS  {} 
--#SEVERITY   INFORMATIONAL 

::= { petevts 1273733 }
  
-- EISA Fail Safe Timeout Event Cleared 
trapCriticalInterruptEISAFailSafeTimeoutCleared NOTIFICATION-TYPE 
STATUS current
-- ENTERPRISE petevts 
DESCRIPTION  
 "Critical Interrupt, EISA Fail Safe Timeout Event Cleared" 

--#TYPE       "Critical Interrupts Event" 
--#SUMMARY    "Critical Interrupt, EISA Fail Safe Timeout Event Cleared" 
--#ARGUMENTS  {} 
--#SEVERITY   INFORMATIONAL 

::= { petevts 1273734 }

-- Bus Correctable Error Cleared 
trapCriticalInterruptBusCorrectableErrorCleared NOTIFICATION-TYPE 
STATUS current
-- ENTERPRISE petevts 
DESCRIPTION  
 "Critical Interrupt, Bus Correctable Error Cleared" 

--#TYPE       "Critical Interrupts Event" 
--#SUMMARY    "Critical Interrupt, Bus Correctable Error Cleared" 
--#ARGUMENTS  {} 
--#SEVERITY   INFORMATIONAL 

::= { petevts 1273735 }

-- Bus uncorrectable error Cleared 
trapCriticalInterruptBusUncorrectCleared NOTIFICATION-TYPE 
STATUS current
-- ENTERPRISE petevts 
DESCRIPTION  
 "Critical Interrupt, Bus Uncorrectable error Cleared" 

--#TYPE       "Critical Interrupts Event" 
--#SUMMARY    "Critical Interrupt, Bus Uncorrectable error Cleared" 
--#ARGUMENTS  {} 
--#SEVERITY   INFORMATIONAL 

::= { petevts 1273736 }

-- Fatal non-maskable interrupt (NMI) Cleared 
trapCriticalInterruptFatalNMICleared NOTIFICATION-TYPE 
STATUS current
-- ENTERPRISE petevts 
DESCRIPTION  
 "Critical Interrupt, Fatal NMI error Cleared" 

--#TYPE       "Critical Interrupts Event" 
--#SUMMARY    "Critical Interrupt, Fatal NMI error Cleared" 
--#ARGUMENTS  {} 
--#SEVERITY   INFORMATIONAL 

::= { petevts 1273737 }
 
-- Bus Fatal Error Cleared 
trapCriticalInterruptFatalBusErrorCleared NOTIFICATION-TYPE 
STATUS current
-- ENTERPRISE petevts 
DESCRIPTION  
 "Critical Interrupt, Bus Fatal Error Cleared" 

--#TYPE       "Critical Interrupts Event" 
--#SUMMARY    "Critical Interrupt, Bus Fatal Error Cleared" 
--#ARGUMENTS  {} 
--#SEVERITY   INFORMATIONAL 

::= { petevts 1273738 }
 
-- Bus Degraded (bus operating in a degraded performance state) Event Cleared 
trapCriticalInterruptBusDegradedEventCleared NOTIFICATION-TYPE 
STATUS current
-- ENTERPRISE petevts 
DESCRIPTION  
 "Critical Interrupt, Bus Degraded (bus operating in a degraded performance state) Event Cleared"  

--#TYPE       "Critical Interrupts Event" 
--#SUMMARY    "Critical Interrupt, Bus Degraded (bus operating in a degraded performance state) Event Cleared" 
--#ARGUMENTS  {} 
--#SEVERITY   INFORMATIONAL 

::= { petevts 1273739 }
 
-- ********************************************** 
-- *		Button/Switch			* 
-- ********************************************** 

-- Power Button pressed 
trapPowerButtonPressed NOTIFICATION-TYPE 
STATUS current
-- ENTERPRISE petevts 
DESCRIPTION 
 "Power Button pressed." 

--#TYPE       "Button/Switch Event" 
--#SUMMARY    "Power Button pressed." 
--#ARGUMENTS  {} 
--#SEVERITY   INFORMATIONAL 

::= { petevts 1339136 }

-- Sleep Button pressed 
trapSleepButtonPressed NOTIFICATION-TYPE 
STATUS current
-- ENTERPRISE petevts 
DESCRIPTION 
 "Sleep Button pressed." 

--#TYPE       "Button/Switch Event" 
--#SUMMARY    "Sleep Button pressed." 
--#ARGUMENTS  {} 
--#SEVERITY   INFORMATIONAL 

::= { petevts 1339137 }

-- Reset Button pressed 
trapResetButtonPressed NOTIFICATION-TYPE 
STATUS current
-- ENTERPRISE petevts 
DESCRIPTION 
 "Reset Button pressed." 

--#TYPE       "Button/Switch Event" 
--#SUMMARY    "Reset Button pressed." 
--#ARGUMENTS  {} 
--#SEVERITY   INFORMATIONAL 

::= { petevts 1339138 }

-- FRU latch open 
trapFRULatchOpen NOTIFICATION-TYPE 
STATUS current
-- ENTERPRISE petevts 
DESCRIPTION 
 "FRU latch open (Switch indicating FRU latch is in unlatched position and FRU is mechanically removable)" 

--#TYPE       "Button/Switch Event" 
--#SUMMARY    "FRU latch open" 
--#ARGUMENTS  {} 
--#SEVERITY   INFORMATIONAL 

::= { petevts 1339139 }

-- FRU service request button 
trapFRUServiceRequestButton NOTIFICATION-TYPE 
STATUS current
-- ENTERPRISE petevts 
DESCRIPTION 
 "FRU service request button" 

--#TYPE       "Button/Switch Event" 
--#SUMMARY    "FRU service request button" 
--#ARGUMENTS  {} 
--#SEVERITY   INFORMATIONAL 

::= { petevts 1339140 }

-- Power Button Released 
trapPowerButtonReleased NOTIFICATION-TYPE 
STATUS current
-- ENTERPRISE petevts 
DESCRIPTION 
 "Power Button Released." 

--#TYPE       "Button/Switch Event" 
--#SUMMARY    "Power Button Released." 
--#ARGUMENTS  {} 
--#SEVERITY   INFORMATIONAL 

::= { petevts 1339264 }

-- Sleep Button Released 
trapSleepButtonReleased NOTIFICATION-TYPE 
STATUS current
-- ENTERPRISE petevts 
DESCRIPTION 
 "Sleep Button Released." 

--#TYPE       "Button/Switch Event" 
--#SUMMARY    "Sleep Button Released." 
--#ARGUMENTS  {} 
--#SEVERITY   INFORMATIONAL 

::= { petevts 1339265 }

-- Reset Button Released 
trapResetButtonReleased NOTIFICATION-TYPE 
STATUS current
-- ENTERPRISE petevts 
DESCRIPTION 
 "Reset Button Released." 

--#TYPE       "Button/Switch Event" 
--#SUMMARY    "Reset Button Released." 
--#ARGUMENTS  {} 
--#SEVERITY   INFORMATIONAL 

::= { petevts 1339266 }

-- FRU latch Closed 
trapFRULatchClosed NOTIFICATION-TYPE 
STATUS current
-- ENTERPRISE petevts 
DESCRIPTION 
 "FRU latch Closed (Switch indicating FRU latch is in latched position)" 

--#TYPE       "Button/Switch Event" 
--#SUMMARY    "FRU latch Closed" 
--#ARGUMENTS  {} 
--#SEVERITY   INFORMATIONAL 

::= { petevts 1339267 }

-- FRU service request button Released 
trapFRUServiceRequestButtonReleased NOTIFICATION-TYPE 
STATUS current
-- ENTERPRISE petevts 
DESCRIPTION 
 "FRU service request button Released" 

--#TYPE       "Button/Switch Event" 
--#SUMMARY    "FRU service request button Released" 
--#ARGUMENTS  {} 
--#SEVERITY   INFORMATIONAL 

::= { petevts 1339268 }

-- ********************************************** 
-- *		Module/Board			* 
-- ********************************************** 
-- Module/Board State Deasserted 
trapBoardStateDeasserted NOTIFICATION-TYPE 
STATUS current
-- ENTERPRISE petevts 
DESCRIPTION 
 "Module/Board State Deasserted" 

--#TYPE       "Module/Board Event" 
--#SUMMARY    "Module/Board State Deasserted" 
--#ARGUMENTS  {} 
--#SEVERITY   INFORMATIONAL 

::= { petevts 1377024 }

-- Module/Board State Asserted 
trapBoardStateAsserted NOTIFICATION-TYPE 
STATUS current
-- ENTERPRISE petevts 
DESCRIPTION 
 "Module/Board State Asserted" 

--#TYPE       "Module/Board Event" 
--#SUMMARY    "Module/Board State Asserted" 
--#ARGUMENTS  {} 
--#SEVERITY   INFORMATIONAL 

::= { petevts 1377025 }

-- Module/Board Predictive Failure Deasserted 
trapBoardPredictiveFailureDeasserted NOTIFICATION-TYPE 
STATUS current
-- ENTERPRISE petevts 
DESCRIPTION 
 "Module/Board Predictive Failure Deasserted" 

--#TYPE       "Module/Board Event" 
--#SUMMARY    "Module/Board Predictive Failure Deasserted" 
--#ARGUMENTS  {} 
--#SEVERITY   INFORMATIONAL 

::= { petevts 1377280 }

-- Module/Board Predictive Failure Asserted 
trapBoardPredictiveFailureAsserted NOTIFICATION-TYPE 
STATUS current
-- ENTERPRISE petevts 
DESCRIPTION 
 "Module/Board Predictive Failure Asserted" 

--#TYPE       "Module/Board Event" 
--#SUMMARY    "Module/Board Predictive Failure Asserted" 
--#ARGUMENTS  {} 
--#SEVERITY   INFORMATIONAL 

::= { petevts 1377281 }

-- ********************************************** 
-- *		Microcontroller/Coprocessor			* 
-- ********************************************** 
-- Microcontroller/Coprocessor State Deasserted 
trapMicrocontrollerStateDeasserted NOTIFICATION-TYPE 
STATUS current
-- ENTERPRISE petevts 
DESCRIPTION 
 "Microcontroller/Coprocessor State Deasserted" 

--#TYPE       "Microcontroller/Coprocessor Event" 
--#SUMMARY    "Microcontroller/Coprocessor State Deasserted" 
--#ARGUMENTS  {} 
--#SEVERITY   INFORMATIONAL 

::= { petevts 1442560 }

-- Microcontroller/Coprocessor State Asserted 
trapMicrocontrollerStateAsserted NOTIFICATION-TYPE 
STATUS current
-- ENTERPRISE petevts 
DESCRIPTION 
 "Microcontroller/Coprocessor State Asserted" 

--#TYPE       "Microcontroller/Coprocessor Event" 
--#SUMMARY    "Microcontroller/Coprocessor State Asserted" 
--#ARGUMENTS  {} 
--#SEVERITY   INFORMATIONAL 

::= { petevts 1442561 }

-- Microcontroller/Coprocessor Predictive Failure Deasserted 
trapMicrocontrollerPredictiveFailureDeasserted NOTIFICATION-TYPE 
STATUS current
-- ENTERPRISE petevts 
DESCRIPTION 
 "Microcontroller/Coprocessor Predictive Failure Deasserted" 

--#TYPE       "Microcontroller/Coprocessor Event" 
--#SUMMARY    "Microcontroller/Coprocessor Predictive Failure Deasserted" 
--#ARGUMENTS  {} 
--#SEVERITY   INFORMATIONAL 

::= { petevts 1442816 }

-- Microcontroller/Coprocessor Predictive Failure Asserted 
trapMicrocontrollerPredictiveFailureAsserted NOTIFICATION-TYPE 
STATUS current
-- ENTERPRISE petevts 
DESCRIPTION 
 "Microcontroller/Coprocessor Predictive Failure Asserted" 

--#TYPE       "Microcontroller/Coprocessor Event" 
--#SUMMARY    "Microcontroller/Coprocessor Predictive Failure Asserted" 
--#ARGUMENTS  {} 
--#SEVERITY   INFORMATIONAL 

::= { petevts 1442817 }

-- ********************************************** 
-- *		Add-in Card			* 
-- ********************************************** 
-- Add-in Card State Deasserted 
trapAddInCardStateDeasserted NOTIFICATION-TYPE 
STATUS current
-- ENTERPRISE petevts 
DESCRIPTION 
 "Add-in Card State Deasserted" 

--#TYPE       "Add-in Card Event" 
--#SUMMARY    "Add-in Card State Deasserted" 
--#ARGUMENTS  {} 
--#SEVERITY   INFORMATIONAL 

::= { petevts 1508096 }

-- Add-in Card State Asserted 
trapAddInCardStateAsserted NOTIFICATION-TYPE 
STATUS current
-- ENTERPRISE petevts 
DESCRIPTION 
 "Add-in Card State Asserted" 

--#TYPE       "Add-in Card Event" 
--#SUMMARY    "Add-in Card State Asserted" 
--#ARGUMENTS  {} 
--#SEVERITY   INFORMATIONAL 

::= { petevts 1508097 }

-- Add-in Card Predictive Failure Deasserted 
trapAddInCardPredictiveFailureDeasserted NOTIFICATION-TYPE 
STATUS current
-- ENTERPRISE petevts 
DESCRIPTION 
 "Add-in Card Predictive Failure Deasserted" 

--#TYPE       "Add-in Card Event" 
--#SUMMARY    "Add-in Card Predictive Failure Deasserted" 
--#ARGUMENTS  {} 
--#SEVERITY   INFORMATIONAL 

::= { petevts 1508352 }

-- Add-in Card Predictive Failure Asserted 
trapAddInCardPredictiveFailureAsserted NOTIFICATION-TYPE 
STATUS current
-- ENTERPRISE petevts 
DESCRIPTION 
 "Add-in Card Predictive Failure Asserted" 

--#TYPE       "Add-in Card Event" 
--#SUMMARY    "Add-in Card Predictive Failure Asserted" 
--#ARGUMENTS  {} 
--#SEVERITY   INFORMATIONAL 

::= { petevts 1508353 }

-- ********************************************** 
-- *		Chassis			* 
-- ********************************************** 
-- Chassis State Deasserted 
trapChassisStateDeasserted NOTIFICATION-TYPE 
STATUS current
-- ENTERPRISE petevts 
DESCRIPTION 
 "Chassis State Deasserted" 

--#TYPE       "Chassis Event" 
--#SUMMARY    "Chassis State Deasserted" 
--#ARGUMENTS  {} 
--#SEVERITY   INFORMATIONAL 

::= { petevts 1573632 }

-- Chassis State Asserted 
trapChassisStateAsserted NOTIFICATION-TYPE 
STATUS current
-- ENTERPRISE petevts 
DESCRIPTION 
 "Chassis State Asserted" 

--#TYPE       "Chassis Event" 
--#SUMMARY    "Chassis State Asserted" 
--#ARGUMENTS  {} 
--#SEVERITY   INFORMATIONAL 

::= { petevts 1573633 }

-- Chassis Predictive Failure Deasserted 
trapChassisPredictiveFailureDeasserted NOTIFICATION-TYPE 
STATUS current
-- ENTERPRISE petevts 
DESCRIPTION 
 "Chassis Predictive Failure Deasserted" 

--#TYPE       "Chassis Event" 
--#SUMMARY    "Chassis Predictive Failure Deasserted" 
--#ARGUMENTS  {} 
--#SEVERITY   INFORMATIONAL 

::= { petevts 1573888 }

-- Chassis Predictive Failure Asserted 
trapChassisPredictiveFailureAsserted NOTIFICATION-TYPE 
STATUS current
-- ENTERPRISE petevts 
DESCRIPTION 
 "Chassis Predictive Failure Asserted" 

--#TYPE       "Chassis Event" 
--#SUMMARY    "Chassis Predictive Failure Asserted" 
--#ARGUMENTS  {} 
--#SEVERITY   INFORMATIONAL 

::= { petevts 1573889 }

-- ********************************************** 
-- *		Chip Set			* 
-- ********************************************** 
-- Chip Set State Deasserted 
trapChipSetStateDeasserted NOTIFICATION-TYPE 
STATUS current
-- ENTERPRISE petevts 
DESCRIPTION 
 "Chip Set State Deasserted" 

--#TYPE       "Chip Set Event" 
--#SUMMARY    "Chip Set State Deasserted" 
--#ARGUMENTS  {} 
--#SEVERITY   INFORMATIONAL 

::= { petevts 1639168 }

-- Chip Set State Asserted 
trapChipSetStateAsserted NOTIFICATION-TYPE 
STATUS current
-- ENTERPRISE petevts 
DESCRIPTION 
 "Chip Set State Asserted" 

--#TYPE       "Chip Set Event" 
--#SUMMARY    "Chip Set State Asserted" 
--#ARGUMENTS  {} 
--#SEVERITY   INFORMATIONAL 

::= { petevts 1639169 }

-- Chip Set Predictive Failure Deasserted 
trapChipSetPredictiveFailureDeasserted NOTIFICATION-TYPE 
STATUS current
-- ENTERPRISE petevts 
DESCRIPTION 
 "Chip Set Predictive Failure Deasserted" 

--#TYPE       "Chip Set Event" 
--#SUMMARY    "Chip Set Predictive Failure Deasserted" 
--#ARGUMENTS  {} 
--#SEVERITY   INFORMATIONAL 

::= { petevts 1639424 }

-- Chip Set Predictive Failure Asserted 
trapChipSetPredictiveFailureAsserted NOTIFICATION-TYPE 
STATUS current
-- ENTERPRISE petevts 
DESCRIPTION 
 "Chip Set Predictive Failure Asserted" 

--#TYPE       "Chip Set Event" 
--#SUMMARY    "Chip Set Predictive Failure Asserted" 
--#ARGUMENTS  {} 
--#SEVERITY   INFORMATIONAL 

::= { petevts 1639425 }

-- Soft Power Control Failure 
trapSoftPowerControlFailure NOTIFICATION-TYPE 
STATUS current
-- ENTERPRISE petevts 
DESCRIPTION 
 "Chip Set did not respond to BMC request to change system power state." 

--#TYPE       "Chip Set Event" 
--#SUMMARY    "Soft Power Control Failure" 
--#ARGUMENTS  {} 
--#SEVERITY   WARNING 

::= { petevts 1666816 }

-- Thermal Trip Occured 
trapThermalTrip NOTIFICATION-TYPE 
STATUS current
-- ENTERPRISE petevts 
DESCRIPTION 
 "Thermal Trip Occured" 

--#TYPE       "Chip Set Event" 
--#SUMMARY    "Thermal Trip Occured" 
--#ARGUMENTS  {} 
--#SEVERITY   WARNING 

::= { petevts 1666817 }

-- Soft Power Control Failure Cleared 
trapSoftPowerControlFailureCleared NOTIFICATION-TYPE 
STATUS current
-- ENTERPRISE petevts 
DESCRIPTION 
 "Chip Set started responding to BMC request to change system power state." 

--#TYPE       "Chip Set Event" 
--#SUMMARY    "Soft Power Control Failure Cleared" 
--#ARGUMENTS  {} 
--#SEVERITY   INFORMATIONAL 

::= { petevts 1666944 }

-- Thermal Trip Cleared 
trapThermalTripCleared NOTIFICATION-TYPE 
STATUS current
-- ENTERPRISE petevts 
DESCRIPTION 
 "Thermal Trip Cleared" 

--#TYPE       "Chip Set Event" 
--#SUMMARY    "Thermal Trip Cleared" 
--#ARGUMENTS  {} 
--#SEVERITY   INFORMATIONAL 

::= { petevts 1666945 }

-- ********************************************** 
-- *		Other FRU			* 
-- ********************************************** 
-- FRU State Deasserted 
trapFRUStateDeasserted NOTIFICATION-TYPE 
STATUS current
-- ENTERPRISE petevts 
DESCRIPTION 
 "FRU State Deasserted" 

--#TYPE       "Other FRU Event" 
--#SUMMARY    "FRU State Deasserted" 
--#ARGUMENTS  {} 
--#SEVERITY   INFORMATIONAL 

::= { petevts 1704704 }

-- FRU State Asserted 
trapFRUStateAsserted NOTIFICATION-TYPE 
STATUS current
-- ENTERPRISE petevts 
DESCRIPTION 
 "FRU State Asserted" 

--#TYPE       "Other FRU Event" 
--#SUMMARY    "FRU State Asserted" 
--#ARGUMENTS  {} 
--#SEVERITY   INFORMATIONAL 

::= { petevts 1704705 }

-- FRU Predictive Failure Deasserted 
trapFRUPredictiveFailureDeasserted NOTIFICATION-TYPE 
STATUS current
-- ENTERPRISE petevts 
DESCRIPTION 
 "FRU Predictive Failure Deasserted" 

--#TYPE       "Other FRU Event" 
--#SUMMARY    "FRU Predictive Failure Deasserted" 
--#ARGUMENTS  {} 
--#SEVERITY   INFORMATIONAL 

::= { petevts 1704960 }

-- FRU Predictive Failure Asserted 
trapFRUPredictiveFailureAsserted NOTIFICATION-TYPE 
STATUS current
-- ENTERPRISE petevts 
DESCRIPTION 
 "FRU Predictive Failure Asserted" 

--#TYPE       "Other FRU Event" 
--#SUMMARY    "FRU Predictive Failure Asserted" 
--#ARGUMENTS  {} 
--#SEVERITY   INFORMATIONAL 

::= { petevts 1704961 }

-- ********************************************** 
-- *		Cable / Interconnect			* 
-- ********************************************** 
-- Cable / Interconnect State Deasserted 
trapCableStateDeasserted NOTIFICATION-TYPE 
STATUS current
-- ENTERPRISE petevts 
DESCRIPTION 
 "Cable / Interconnect State Deasserted" 

--#TYPE       "Other Cable / Interconnect Event" 
--#SUMMARY    "Cable / Interconnect State Deasserted" 
--#ARGUMENTS  {} 
--#SEVERITY   INFORMATIONAL 

::= { petevts 1770240 }

-- Cable / Interconnect State Asserted 
trapCableStateAsserted NOTIFICATION-TYPE 
STATUS current
-- ENTERPRISE petevts 
DESCRIPTION 
 "Cable / Interconnect State Asserted" 

--#TYPE       "Other Cable / Interconnect Event" 
--#SUMMARY    "Cable / Interconnect State Asserted" 
--#ARGUMENTS  {} 
--#SEVERITY   INFORMATIONAL 

::= { petevts 1770241 }

-- Cable / Interconnect Predictive Failure Deasserted 
trapCablePredictiveFailureDeasserted NOTIFICATION-TYPE 
STATUS current
-- ENTERPRISE petevts 
DESCRIPTION 
 "Cable / Interconnect Predictive Failure Deasserted" 

--#TYPE       "Other Cable / Interconnect Event" 
--#SUMMARY    "Cable / Interconnect Predictive Failure Deasserted" 
--#ARGUMENTS  {} 
--#SEVERITY   INFORMATIONAL 

::= { petevts 1770496 }

-- Cable / Interconnect Predictive Failure Asserted 
trapCablePredictiveFailureAsserted NOTIFICATION-TYPE 
STATUS current
-- ENTERPRISE petevts 
DESCRIPTION 
 "Cable / Interconnect Predictive Failure Asserted" 

--#TYPE       "Other Cable / Interconnect Event" 
--#SUMMARY    "Cable / Interconnect Predictive Failure Asserted" 
--#ARGUMENTS  {} 
--#SEVERITY   INFORMATIONAL 

::= { petevts 1770497 }

-- Cable/Interconnect is connected 
trapCableConnected NOTIFICATION-TYPE 
STATUS current
-- ENTERPRISE petevts 
DESCRIPTION 
 "Cable/Interconnect is connected" 

--#TYPE       "Other Cable / Interconnect Event" 
--#SUMMARY    "Cable/Interconnect is connected" 
--#ARGUMENTS  {} 
--#SEVERITY   INFORMATIONAL 

::= { petevts 1797888 }

-- Configuration Error 
trapConfigurationError NOTIFICATION-TYPE 
STATUS current
-- ENTERPRISE petevts 
DESCRIPTION 
 "Configuration Error - Incorrect cable connected / Incorrect interconnection" 

--#TYPE       "Other Cable / Interconnect Event" 
--#SUMMARY    "Configuration Error" 
--#ARGUMENTS  {} 
--#SEVERITY   INFORMATIONAL 

::= { petevts 1797889 }

-- Cable/Interconnect is disconnected 
trapCableDisConnected NOTIFICATION-TYPE 
STATUS current
-- ENTERPRISE petevts 
DESCRIPTION 
 "Cable/Interconnect is disconnected" 

--#TYPE       "Other Cable / Interconnect Event" 
--#SUMMARY    "Cable/Interconnect is disconnected" 
--#ARGUMENTS  {} 
--#SEVERITY   WARNING 

::= { petevts 1798016 }

-- Configuration Error Cleared 
trapConfigurationErrorCleared NOTIFICATION-TYPE 
STATUS current
-- ENTERPRISE petevts 
DESCRIPTION 
 "Configuration Error Cleared" 

--#TYPE       "Other Cable / Interconnect Event" 
--#SUMMARY    "Configuration Error Cleared" 
--#ARGUMENTS  {} 
--#SEVERITY   INFORMATIONAL 

::= { petevts 1798017 }

-- ********************************************** 
-- *		Terminator			* 
-- ********************************************** 
-- Terminator State Deasserted 
trapTerminatorStateDeasserted NOTIFICATION-TYPE 
STATUS current
-- ENTERPRISE petevts 
DESCRIPTION 
 "Terminator State Deasserted" 

--#TYPE       "Terminator Event" 
--#SUMMARY    "Terminator State Deasserted" 
--#ARGUMENTS  {} 
--#SEVERITY   INFORMATIONAL 

::= { petevts 1835776 }

-- Terminator State Asserted 
trapTerminatorStateAsserted NOTIFICATION-TYPE 
STATUS current
-- ENTERPRISE petevts 
DESCRIPTION 
 "Terminator State Asserted" 

--#TYPE       "Terminator Event" 
--#SUMMARY    "Terminator State Asserted" 
--#ARGUMENTS  {} 
--#SEVERITY   INFORMATIONAL 

::= { petevts 1835777 }

-- Terminator Predictive Failure Deasserted 
trapTerminatorPredictiveFailureDeasserted NOTIFICATION-TYPE 
STATUS current
-- ENTERPRISE petevts 
DESCRIPTION 
 "Terminator Predictive Failure Deasserted" 

--#TYPE       "Terminator Event" 
--#SUMMARY    "Terminator Predictive Failure Deasserted" 
--#ARGUMENTS  {} 
--#SEVERITY   INFORMATIONAL 

::= { petevts 1836032 }

-- Terminator Predictive Failure Asserted 
trapTerminatorPredictiveFailureAsserted NOTIFICATION-TYPE 
STATUS current
-- ENTERPRISE petevts 
DESCRIPTION 
 "Terminator Predictive Failure Asserted" 

--#TYPE       "Terminator Event" 
--#SUMMARY    "Terminator Predictive Failure Asserted" 
--#ARGUMENTS  {} 
--#SEVERITY   INFORMATIONAL 

::= { petevts 1836033 }

-- ********************************************** 
-- *		System Boot / Restart Initiated		* 
-- ********************************************** 

-- System Boot / Restart Initiated by power up 
trapSystemBootByPowerUp NOTIFICATION-TYPE 
STATUS current
-- ENTERPRISE petevts 
DESCRIPTION 
 "System Boot / Restart Initiated by power up" 

--#TYPE       "System Boot / Restart Event" 
--#SUMMARY    "System Boot / Restart Initiated by power up" 
--#ARGUMENTS  {} 
--#SEVERITY   INFORMATIONAL 

::= { petevts 1928960 }

-- System Boot / Restart Initiated by Hard Reset 
trapSystemBootByHardReset NOTIFICATION-TYPE 
STATUS current
-- ENTERPRISE petevts 
DESCRIPTION 
 "System Boot / Restart Initiated by Hard Reset" 

--#TYPE       "System Boot / Restart Event" 
--#SUMMARY    "System Boot / Restart Initiated by Hard Reset" 
--#ARGUMENTS  {} 
--#SEVERITY   INFORMATIONAL 

::= { petevts 1928961 }

-- System Boot / Restart Initiated by Warm Reset 
trapSystemBootByWarmReset NOTIFICATION-TYPE 
STATUS current
-- ENTERPRISE petevts 
DESCRIPTION 
 "System Boot / Restart Initiated by Warm Reset" 

--#TYPE       "System Boot / Restart Event" 
--#SUMMARY    "System Boot / Restart Initiated by Warm Reset" 
--#ARGUMENTS  {} 
--#SEVERITY   INFORMATIONAL 

::= { petevts 1928962 }

-- System Boot / Restart - User requested PXE boot 
trapUserRequestedPXEBoot NOTIFICATION-TYPE 
STATUS current
-- ENTERPRISE petevts 
DESCRIPTION 
 "System Boot / Restart - User requested PXE boot" 

--#TYPE       "System Boot / Restart Event" 
--#SUMMARY    "System Boot / Restart - User requested PXE boot" 
--#ARGUMENTS  {} 
--#SEVERITY   INFORMATIONAL 

::= { petevts 1928963 }

-- System Boot / Restart - Automatic boot to diagnostic 
trapAutomaticDiagnosticBoot NOTIFICATION-TYPE 
STATUS current
-- ENTERPRISE petevts 
DESCRIPTION 
 "System Boot / Restart - Automatic boot to diagnostic" 

--#TYPE       "System Boot / Restart Event" 
--#SUMMARY    "System Boot / Restart - Automatic boot to diagnostic" 
--#ARGUMENTS  {} 
--#SEVERITY   INFORMATIONAL 

::= { petevts 1928964 }

-- System Boot / Restart - OS / run-time software initiated hard reset 
trapOSInitiatedHardReset NOTIFICATION-TYPE 
STATUS current
-- ENTERPRISE petevts 
DESCRIPTION 
 "System Boot / Restart - OS / run-time software initiated hard reset" 

--#TYPE       "System Boot / Restart Event" 
--#SUMMARY    "System Boot / Restart - OS / run-time software initiated hard reset" 
--#ARGUMENTS  {} 
--#SEVERITY   INFORMATIONAL 

::= { petevts 1928965 }

-- System Boot / Restart - OS / run-time software initiated Warm reset 
trapOSInitiatedWarmReset NOTIFICATION-TYPE 
STATUS current
-- ENTERPRISE petevts 
DESCRIPTION 
 "System Boot / Restart - OS / run-time software initiated Warm reset" 

--#TYPE       "System Boot / Restart Event" 
--#SUMMARY    "System Boot / Restart - OS / run-time software initiated Warm reset" 
--#ARGUMENTS  {} 
--#SEVERITY   INFORMATIONAL 

::= { petevts 1928966 }

-- System Boot / Restart - System Restart 
trapSystemRestart NOTIFICATION-TYPE 
STATUS current
-- ENTERPRISE petevts 
DESCRIPTION 
 "System Boot / Restart - Restart cause per Get System Restart Cause command" 

--#TYPE       "System Boot / Restart Event" 
--#SUMMARY    "System Boot / Restart - Restart cause per Get System Restart Cause command" 
--#ARGUMENTS  {} 
--#SEVERITY   INFORMATIONAL 

::= { petevts 1928967 }

-- System Boot / Restart Initiated by power up Deasserted 
trapSystemBootByPowerUpDeasserted NOTIFICATION-TYPE 
STATUS current
-- ENTERPRISE petevts 
DESCRIPTION 
 "System Boot / Restart Initiated by power up Deasserted" 

--#TYPE       "System Boot / Restart Event" 
--#SUMMARY    "System Boot / Restart Initiated by power up Deasserted" 
--#ARGUMENTS  {} 
--#SEVERITY   INFORMATIONAL 

::= { petevts 1929088 }

-- System Boot / Restart Initiated by Hard Reset Deasserted 
trapSystemBootByHardResetDeasserted NOTIFICATION-TYPE 
STATUS current
-- ENTERPRISE petevts 
DESCRIPTION 
 "System Boot / Restart Initiated by Hard Reset Deasserted" 

--#TYPE       "System Boot / Restart Event" 
--#SUMMARY    "System Boot / Restart Initiated by Hard Reset Deasserted" 
--#ARGUMENTS  {} 
--#SEVERITY   INFORMATIONAL 

::= { petevts 1929089 }

-- System Boot / Restart Initiated by Warm Reset Deasserted 
trapSystemBootByWarmResetDeasserted NOTIFICATION-TYPE 
STATUS current
-- ENTERPRISE petevts 
DESCRIPTION 
 "System Boot / Restart Initiated by Warm Reset Deasserted" 

--#TYPE       "System Boot / Restart Event" 
--#SUMMARY    "System Boot / Restart Initiated by Warm Reset Deasserted" 
--#ARGUMENTS  {} 
--#SEVERITY   INFORMATIONAL 

::= { petevts 1929090 }

-- System Boot / Restart - User requested PXE boot Deasserted 
trapUserRequestedPXEBootDeasserted NOTIFICATION-TYPE 
STATUS current
-- ENTERPRISE petevts 
DESCRIPTION 
 "System Boot / Restart - User requested PXE boot Deasserted" 

--#TYPE       "System Boot / Restart Event" 
--#SUMMARY    "System Boot / Restart - User requested PXE boot Deasserted" 
--#ARGUMENTS  {} 
--#SEVERITY   INFORMATIONAL 

::= { petevts 1929091 }

-- System Boot / Restart - Automatic boot to diagnostic Deasserted 
trapAutomaticDiagnosticBootDeasserted NOTIFICATION-TYPE 
STATUS current
-- ENTERPRISE petevts 
DESCRIPTION 
 "System Boot / Restart - Automatic boot to diagnostic Deasserted" 

--#TYPE       "System Boot / Restart Event" 
--#SUMMARY    "System Boot / Restart - Automatic boot to diagnostic Deasserted" 
--#ARGUMENTS  {} 
--#SEVERITY   INFORMATIONAL 

::= { petevts 1929092 }

-- System Boot / Restart - OS / run-time software initiated hard reset Deasserted 
trapOSInitiatedHardResetDeasserted NOTIFICATION-TYPE 
STATUS current
-- ENTERPRISE petevts 
DESCRIPTION 
 "System Boot / Restart - OS / run-time software initiated hard reset Deasserted" 

--#TYPE       "System Boot / Restart Event" 
--#SUMMARY    "System Boot / Restart - OS / run-time software initiated hard reset Deasserted" 
--#ARGUMENTS  {} 
--#SEVERITY   INFORMATIONAL 

::= { petevts 1929093 }

-- System Boot / Restart - OS / run-time software initiated Warm reset Deasserted 
trapOSInitiatedWarmResetDeasserted NOTIFICATION-TYPE 
STATUS current
-- ENTERPRISE petevts 
DESCRIPTION 
 "System Boot / Restart - OS / run-time software initiated Warm reset Deasserted" 

--#TYPE       "System Boot / Restart Event" 
--#SUMMARY    "System Boot / Restart - OS / run-time software initiated Warm reset Deasserted" 
--#ARGUMENTS  {} 
--#SEVERITY   INFORMATIONAL 

::= { petevts 1929094 }

-- System Boot / Restart - System Restart Deasserted 
trapSystemRestartDeasserted NOTIFICATION-TYPE 
STATUS current
-- ENTERPRISE petevts 
DESCRIPTION 
 "System Boot / Restart - Restart cause per Get System Restart Cause command Deasserted" 

--#TYPE       "System Boot / Restart Event" 
--#SUMMARY    "System Boot / Restart - Restart cause per Get System Restart Cause command Deasserted" 
--#ARGUMENTS  {} 
--#SEVERITY   INFORMATIONAL 

::= { petevts 1929095 }

-- ********************************************** 
-- *		Boot Error			* 
-- ********************************************** 

-- Boot Error - No bootable media 
trapNoBootableMedia NOTIFICATION-TYPE 
STATUS current
-- ENTERPRISE petevts 
DESCRIPTION 
 "Boot Error - No bootable media" 

--#TYPE       "Boot Error Event" 
--#SUMMARY    "Boot Error - No bootable media" 
--#ARGUMENTS  {} 
--#SEVERITY   CRITICAL 

::= { petevts 1994496 }

-- Boot Error - Non-bootable diskette left in drive 
trapNonBootableDisketteInDrive NOTIFICATION-TYPE 
STATUS current
-- ENTERPRISE petevts 
DESCRIPTION 
 "Boot Error - Non-bootable diskette left in drive" 

--#TYPE       "Boot Error Event" 
--#SUMMARY    "Boot Error - Non-bootable diskette left in drive" 
--#ARGUMENTS  {} 
--#SEVERITY   CRITICAL 

::= { petevts 1994497 }

-- Boot Error - PXE Server not found 
trapPXEServerNotFound NOTIFICATION-TYPE 
STATUS current
-- ENTERPRISE petevts 
DESCRIPTION 
 "Boot Error - PXE Server not found" 

--#TYPE       "Boot Error Event" 
--#SUMMARY    "Boot Error - PXE Server not found" 
--#ARGUMENTS  {} 
--#SEVERITY   CRITICAL 

::= { petevts 1994498  }

-- Boot Error - Invalid boot sector 
trapInvalidBootSector NOTIFICATION-TYPE 
STATUS current
-- ENTERPRISE petevts 
DESCRIPTION 
 "Boot Error - Invalid boot sector" 

--#TYPE       "Boot Error Event" 
--#SUMMARY    "Boot Error - Invalid boot sector" 
--#ARGUMENTS  {} 
--#SEVERITY   CRITICAL 

::= { petevts 1994499 }

-- Boot Error - Timeout waiting for user selection of boot source 
trapTimeoutWaitingUserSelection NOTIFICATION-TYPE 
STATUS current
-- ENTERPRISE petevts 
DESCRIPTION 
 "Boot Error - Timeout waiting for user selection of boot source" 

--#TYPE       "Boot Error Event" 
--#SUMMARY    "Boot Error - Timeout waiting for user selection of boot source" 
--#ARGUMENTS  {} 
--#SEVERITY   INFORMATIONAL 

::= { petevts 1994500 }

-- Bootable media found 
trapFoundBootableMedia NOTIFICATION-TYPE 
STATUS current
-- ENTERPRISE petevts 
DESCRIPTION 
 "Found bootable media" 

--#TYPE       "Boot Error Event" 
--#SUMMARY    "Found bootable media" 
--#ARGUMENTS  {} 
--#SEVERITY   INFORMATIONAL 

::= { petevts 1994624 }

-- Bootable diskette Found 
trapFoundBootableDisketteInDrive NOTIFICATION-TYPE 
STATUS current
-- ENTERPRISE petevts 
DESCRIPTION 
 "Bootable diskette Found" 

--#TYPE       "Boot Error Event" 
--#SUMMARY    "Bootable diskette Found" 
--#ARGUMENTS  {} 
--#SEVERITY   INFORMATIONAL 

::= { petevts 1994625 }

-- PXE Server  found 
trapPXEServerFound NOTIFICATION-TYPE 
STATUS current
-- ENTERPRISE petevts 
DESCRIPTION 
 "PXE Server found" 

--#TYPE       "Boot Error Event" 
--#SUMMARY    "PXE Server found" 
--#ARGUMENTS  {} 
--#SEVERITY   INFORMATIONAL 

::= { petevts 1994626  }

-- Found valid boot sector 
trapFoundValidBootSector NOTIFICATION-TYPE 
STATUS current
-- ENTERPRISE petevts 
DESCRIPTION 
 "Found valid boot sector" 

--#TYPE       "Boot Error Event" 
--#SUMMARY    "Found Valid boot sector" 
--#ARGUMENTS  {} 
--#SEVERITY   INFORMATIONAL 

::= { petevts 1994627 }

-- User selected boot source 
trapUserSelectedBootSource NOTIFICATION-TYPE 
STATUS current
-- ENTERPRISE petevts 
DESCRIPTION 
 "User selected boot source" 

--#TYPE       "Boot Error Event" 
--#SUMMARY    "User selected boot source" 
--#ARGUMENTS  {} 
--#SEVERITY   INFORMATIONAL 

::= { petevts 1994628 }

-- ********************************************** 
-- *		OS Boot			* 
-- ********************************************** 
-- A: boot completed 
trapBootCompletedDirectoryA NOTIFICATION-TYPE 
STATUS current
-- ENTERPRISE petevts 
DESCRIPTION 
 "A: boot completed" 

--#TYPE       "OS Boot Event" 
--#SUMMARY    "A: boot completed" 
--#ARGUMENTS  {} 
--#SEVERITY   INFORMATIONAL 

::= { petevts 2060032 }

 -- C: boot completed 
trapBootCompletedDirectoryC NOTIFICATION-TYPE 
STATUS current
-- ENTERPRISE petevts 
DESCRIPTION 
 "C: boot completed" 

--#TYPE       "OS Boot Event" 
--#SUMMARY    "C: boot completed" 
--#ARGUMENTS  {} 
--#SEVERITY   INFORMATIONAL 

::= { petevts 2060033 }

 -- PXE boot completed 
trapPXEBootCompleted NOTIFICATION-TYPE 
STATUS current
-- ENTERPRISE petevts 
DESCRIPTION 
 "PXE boot completed" 

--#TYPE       "OS Boot Event" 
--#SUMMARY    "PXE boot completed" 
--#ARGUMENTS  {} 
--#SEVERITY   INFORMATIONAL 

::= { petevts 2060034 }

 -- Diagnostic boot completed 
trapDiagnosticBootCompleted NOTIFICATION-TYPE 
STATUS current
-- ENTERPRISE petevts 
DESCRIPTION 
 "Diagnostic boot completed" 

--#TYPE       "OS Boot Event" 
--#SUMMARY    "Diagnostic boot completed" 
--#ARGUMENTS  {} 
--#SEVERITY   INFORMATIONAL 

::= { petevts 2060035 }
 
  -- CDROM boot completed 
trapCDROMBootCompleted NOTIFICATION-TYPE 
STATUS current
-- ENTERPRISE petevts 
DESCRIPTION 
 "CDROM boot completed" 

--#TYPE       "OS Boot Event" 
--#SUMMARY    "CDROM boot completed" 
--#ARGUMENTS  {} 
--#SEVERITY   INFORMATIONAL 

::= { petevts 2060036 }

 -- ROM boot completed 
trapROMBootCompleted NOTIFICATION-TYPE 
STATUS current
-- ENTERPRISE petevts 
DESCRIPTION 
 "ROM boot completed" 

--#TYPE       "OS Boot Event" 
--#SUMMARY    "ROM boot completed" 
--#ARGUMENTS  {} 
--#SEVERITY   INFORMATIONAL 

::= { petevts 2060037 }

 -- Boot completed - boot device not specified 
trapBootCompletedUnknownSource NOTIFICATION-TYPE 
STATUS current
-- ENTERPRISE petevts 
DESCRIPTION 
 "Boot completed - boot device not specified" 

--#TYPE       "OS Boot Event" 
--#SUMMARY    "Boot completed - boot device not specified" 
--#ARGUMENTS  {} 
--#SEVERITY   INFORMATIONAL 

::= { petevts 2060038 }
 
 -- A: boot incomplete 
trapBootIncompleteDirectoryA NOTIFICATION-TYPE 
STATUS current
-- ENTERPRISE petevts 
DESCRIPTION 
 "A: boot incomplete" 

--#TYPE       "OS Boot Event" 
--#SUMMARY    "A: boot incomplete" 
--#ARGUMENTS  {} 
--#SEVERITY   WARNING 

::= { petevts 2060160 }

 -- C: boot incomplete 
trapBootIncompleteDirectoryC NOTIFICATION-TYPE 
STATUS current
-- ENTERPRISE petevts 
DESCRIPTION 
 "C: boot incomplete" 

--#TYPE       "OS Boot Event" 
--#SUMMARY    "C: boot incomplete" 
--#ARGUMENTS  {} 
--#SEVERITY   WARNING 

::= { petevts 2060161 }

 -- PXE boot Incomplete 
trapPXEBootIncomplete NOTIFICATION-TYPE 
STATUS current
-- ENTERPRISE petevts 
DESCRIPTION 
 "PXE boot Incomplete" 

--#TYPE       "OS Boot Event" 
--#SUMMARY    "PXE boot Incomplete" 
--#ARGUMENTS  {} 
--#SEVERITY   WARNING 

::= { petevts 2060162 }

 -- Diagnostic boot Incomplete 
trapDiagnosticBootIncomplete NOTIFICATION-TYPE 
STATUS current
-- ENTERPRISE petevts 
DESCRIPTION 
 "Diagnostic boot Incomplete" 

--#TYPE       "OS Boot Event" 
--#SUMMARY    "Diagnostic boot Incomplete" 
--#ARGUMENTS  {} 
--#SEVERITY   WARNING 

::= { petevts 2060163 }
 
  -- CDROM boot Incomplete 
trapCDROMBootIncomplete NOTIFICATION-TYPE 
STATUS current
-- ENTERPRISE petevts 
DESCRIPTION 
 "CDROM boot Incomplete" 

--#TYPE       "OS Boot Event" 
--#SUMMARY    "CDROM boot Incomplete" 
--#ARGUMENTS  {} 
--#SEVERITY   WARNING 

::= { petevts 2060164 }

 -- ROM boot Incomplete 
trapROMBootIncomplete NOTIFICATION-TYPE 
STATUS current
-- ENTERPRISE petevts 
DESCRIPTION 
 "ROM boot Incomplete" 

--#TYPE       "OS Boot Event" 
--#SUMMARY    "ROM boot Incomplete" 
--#ARGUMENTS  {} 
--#SEVERITY   WARNING 

::= { petevts 2060165 }

 -- Boot Incomplete - boot device not specified 
trapBootIncompleteUnknownSource NOTIFICATION-TYPE 
STATUS current
-- ENTERPRISE petevts 
DESCRIPTION 
 "Boot Incomplete - boot device not specified" 

--#TYPE       "OS Boot Event" 
--#SUMMARY    "Boot Incomplete - boot device not specified" 
--#ARGUMENTS  {} 
--#SEVERITY   WARNING 

::= { petevts 2060166 }

-- ********************************************** 
-- *		OS Stop / Shutdown			* 
-- ********************************************** 

 -- OS Stop / Shutdown - Stop during OS load / initialization 
trapOSStopDuringLoad NOTIFICATION-TYPE 
STATUS current
-- ENTERPRISE petevts 
DESCRIPTION 
 "OS Stop / Shutdown - Stop during OS load / initialization. Unexpected error uring system startup. Stopped waiting for input or power cycle/reset" 

--#TYPE       "OS Stop / Shutdown Event" 
--#SUMMARY    "OS Stop / Shutdown - Stop during OS load / initialization" 
--#ARGUMENTS  {} 
--#SEVERITY   CRITICAL 

::= { petevts 2125568 }
 
  -- OS Stop / Shutdown - Run-time Critical Stop 
trapOSRuntimeCriticalStop NOTIFICATION-TYPE 
STATUS current
-- ENTERPRISE petevts 
DESCRIPTION 
 "OS Stop / Shutdown - Run-time Critical Stop" 

--#TYPE       "OS Stop / Shutdown Event" 
--#SUMMARY    "OS Stop / Shutdown - Run-time Critical Stop" 
--#ARGUMENTS  {} 
--#SEVERITY   CRITICAL 

::= { petevts 2125569 }

-- OS Stop / Shutdown - Graceful Stop 
trapOSGracefulStop NOTIFICATION-TYPE 
STATUS current
-- ENTERPRISE petevts 
DESCRIPTION 
 "OS Stop / Shutdown - Graceful Stop (system powered up, but normal OS operation has shut down and system is awaiting reset pushbutton, powercycle or other external input)" 

--#TYPE       "OS Stop / Shutdown Event" 
--#SUMMARY    "OS Stop / Shutdown - Graceful Stop" 
--#ARGUMENTS  {} 
--#SEVERITY   INFORMATIONAL 

::= { petevts 2125570 }
  
-- OS Stop / Shutdown - Graceful Shutdown 
trapOSGracefulShutdown NOTIFICATION-TYPE 
STATUS current
-- ENTERPRISE petevts 
DESCRIPTION 
 "OS Stop / Shutdown - Graceful Shutdown (system graceful power down by OS)" 

--#TYPE       "OS Stop / Shutdown Event" 
--#SUMMARY    "OS Stop / Shutdown - Graceful Shutdown" 
--#ARGUMENTS  {} 
--#SEVERITY   INFORMATIONAL 

::= { petevts 2125571 }

-- OS Stop / Shutdown - Soft Shutdown initiated by PEF 
trapOSSoftShutdownInitiatedByPEF NOTIFICATION-TYPE 
STATUS current
-- ENTERPRISE petevts 
DESCRIPTION 
 "OS Stop / Shutdown - Soft Shutdown initiated by PEF" 

--#TYPE       "OS Stop / Shutdown Event" 
--#SUMMARY    "OS Stop / Shutdown - Soft Shutdown initiated by PEF" 
--#ARGUMENTS  {} 
--#SEVERITY   INFORMATIONAL 

::= { petevts 2125572 }

-- OS Stop / Shutdown - Agent Not Responding 
trapOSAgentNotResponding NOTIFICATION-TYPE 
STATUS current
-- ENTERPRISE petevts 
DESCRIPTION 
 "OS Stop / Shutdown - Agent Not Responding" 

--#TYPE       "OS Stop / Shutdown Event" 
--#SUMMARY    "OS Stop / Shutdown - Agent Not Responding" 
--#ARGUMENTS  {} 
--#SEVERITY   CRITICAL 

::= { petevts 2125573 }
 
  -- OS Stop / Shutdown - Stop during OS load / initialization Deasserted 
trapOSStopDuringLoadDeasserted NOTIFICATION-TYPE 
STATUS current
-- ENTERPRISE petevts 
DESCRIPTION 
 "OS Stop / Shutdown - power cycle/reset Done" 

--#TYPE       "OS Stop / Shutdown Event" 
--#SUMMARY    "OS Stop / Shutdown - Stop during OS load / initialization Deasserted" 
--#ARGUMENTS  {} 
--#SEVERITY   INFORMATIONAL 

::= { petevts 2125696 }
 
  -- OS Stop / Shutdown - Run-time INFORMATIONAL Stop Deasserted 
trapOSRuntimeINFORMATIONALStopDeasserted NOTIFICATION-TYPE 
STATUS current
-- ENTERPRISE petevts 
DESCRIPTION 
 "OS Stop / Shutdown -Power Cycle/Reset Done" 

--#TYPE       "OS Stop / Shutdown Event" 
--#SUMMARY    "OS Stop / Shutdown - Run-time INFORMATIONAL Stop Deasserted" 
--#ARGUMENTS  {} 
--#SEVERITY   INFORMATIONAL 

::= { petevts 2125697 }

-- OS Stop / Shutdown - Graceful Stop Deasserted 
trapOSGracefulStopDeasserted NOTIFICATION-TYPE 
STATUS current
-- ENTERPRISE petevts 
DESCRIPTION 
 "OS Stop / Shutdown - System powered up by reset pushbutton, powercycle or other external input" 

--#TYPE       "OS Stop / Shutdown Event" 
--#SUMMARY    "OS Stop / Shutdown - Graceful Stop Deasserted" 
--#ARGUMENTS  {} 
--#SEVERITY   INFORMATIONAL 

::= { petevts 2125698 }
  
-- OS Stop / Shutdown - Graceful Shutdown Deasserted 
trapOSGracefulShutdownDeasserted NOTIFICATION-TYPE 
STATUS current
-- ENTERPRISE petevts 
DESCRIPTION 
 "OS Stop / Shutdown - System powered by reset pushbutton, powercycle or other external input" 

--#TYPE       "OS Stop / Shutdown Event" 
--#SUMMARY    "OS Stop / Shutdown - Graceful Shutdown Deasserted" 
--#ARGUMENTS  {} 
--#SEVERITY   INFORMATIONAL 

::= { petevts 2125699 }

-- OS Stop / Shutdown - Soft Shutdown Deasserted 
trapOSSoftShutdownDeasserted NOTIFICATION-TYPE 
STATUS current
-- ENTERPRISE petevts 
DESCRIPTION 
 "OS Stop / Shutdown - System powered by reset pushbutton, powercycle or other external input" 

--#TYPE       "OS Stop / Shutdown Event" 
--#SUMMARY    "OS Stop / Shutdown - Soft Shutdown Deasserted" 
--#ARGUMENTS  {} 
--#SEVERITY   INFORMATIONAL 

::= { petevts 2125700 }

-- OS Stop / Shutdown - Agent Started Responding 
trapOSAgentNotRespondingDeasserted NOTIFICATION-TYPE 
STATUS current
-- ENTERPRISE petevts 
DESCRIPTION 
 "OS Stop / Shutdown - Agent Started Responding" 

--#TYPE       "OS Stop / Shutdown Event" 
--#SUMMARY    "OS Stop / Shutdown - Agent Started Responding" 
--#ARGUMENTS  {} 
--#SEVERITY   INFORMATIONAL 

::= { petevts 2125701 }

-- ********************************************** 
-- *		Slot / Connector			* 
-- ********************************************** 

-- Slot / Connector - Fault Status asserted 
trapSlotFaultStatusAsserted NOTIFICATION-TYPE 
STATUS current
-- ENTERPRISE petevts 
DESCRIPTION 
 "Slot / Connector - Fault Status asserted" 

--#TYPE       "Slot / Connector Event" 
--#SUMMARY    "Slot / Connector - Fault Status asserted" 
--#ARGUMENTS  {} 
--#SEVERITY   INFORMATIONAL 

::= { petevts 2191104 }

-- Slot / Connector - Identify Status asserted 
trapSlotIdentifyStatusAsserted NOTIFICATION-TYPE 
STATUS current
-- ENTERPRISE petevts 
DESCRIPTION 
 "Slot / Connector - Identify Status asserted" 

--#TYPE       "Slot / Connector Event" 
--#SUMMARY    "Slot / Connector - Identify Status asserted" 
--#ARGUMENTS  {} 
--#SEVERITY   INFORMATIONAL 

::= { petevts 2191105 }

-- Slot / Connector - Device installed/attached 
trapSlotDeviceInstalledOrAttached NOTIFICATION-TYPE 
STATUS current
-- ENTERPRISE petevts 
DESCRIPTION 
 "Slot / Connector - Device installed/attached" 

--#TYPE       "Slot / Connector Event" 
--#SUMMARY    "Slot / Connector - Device installed/attached" 
--#ARGUMENTS  {} 
--#SEVERITY   INFORMATIONAL 

::= { petevts 2191106 }

-- Slot / Connector - Ready for Device Installation 
trapSlotReadyForDeviceInstallation NOTIFICATION-TYPE 
STATUS current
-- ENTERPRISE petevts 
DESCRIPTION 
 "Slot / Connector - Ready for Device Installation. Typically, this means that the slot power is off" 

--#TYPE       "Slot / Connector Event" 
--#SUMMARY    "Slot / Connector - Ready for Device Installation" 
--#ARGUMENTS  {} 
--#SEVERITY   INFORMATIONAL 

::= { petevts 2191107 }

-- Slot / Connector - Ready for Device Removal 
trapSlotReadyForDeviceRemoval NOTIFICATION-TYPE 
STATUS current
-- ENTERPRISE petevts 
DESCRIPTION 
 "Slot / Connector - Ready for Device Removal. Typically, this means that the slot power is off" 

--#TYPE       "Slot / Connector Event" 
--#SUMMARY    "Slot / Connector - Ready for Device Removal" 
--#ARGUMENTS  {} 
--#SEVERITY   INFORMATIONAL 

::= { petevts 2191108 }

-- Slot / Connector - Slot Power is Off 
trapSlotPowerIsOff NOTIFICATION-TYPE 
STATUS current
-- ENTERPRISE petevts 
DESCRIPTION 
 "Slot / Connector - Slot Power is Off" 

--#TYPE       "Slot / Connector Event" 
--#SUMMARY    "Slot / Connector - Slot Power is Off" 
--#ARGUMENTS  {} 
--#SEVERITY   INFORMATIONAL 

::= { petevts 2191109 }

-- Slot / Connector - Device Removal Request 
trapSlotDeviceRemovalRequest NOTIFICATION-TYPE 
STATUS current
-- ENTERPRISE petevts 
DESCRIPTION 
 "Slot / Connector - Device Removal Request" 

--#TYPE       "Slot / Connector Event" 
--#SUMMARY    "Slot / Connector - Device Removal Request" 
--#ARGUMENTS  {} 
--#SEVERITY   INFORMATIONAL 

::= { petevts 2191110 }

-- Slot / Connector - Interlock asserted 
trapSlotInterlockAsserted NOTIFICATION-TYPE 
STATUS current
-- ENTERPRISE petevts 
DESCRIPTION 
 "Slot / Connector - Interlock asserted" 

--#TYPE       "Slot / Connector Event" 
--#SUMMARY    "Slot / Connector - Interlock asserted" 
--#ARGUMENTS  {} 
--#SEVERITY   INFORMATIONAL 

::= { petevts 2191111 }

-- Slot / Connector - Disabled 
trapSlotDisabled NOTIFICATION-TYPE 
STATUS current
-- ENTERPRISE petevts 
DESCRIPTION 
 "Slot / Connector - Disabled" 

--#TYPE       "Slot / Connector Event" 
--#SUMMARY    "Slot / Connector - Disabled" 
--#ARGUMENTS  {} 
--#SEVERITY   INFORMATIONAL 

::= { petevts 2191112 }

-- Slot / Connector - holds spare device 
trapSlotHoldsSpareDevice NOTIFICATION-TYPE 
STATUS current
-- ENTERPRISE petevts 
DESCRIPTION 
 "Slot / Connector - holds spare device" 

--#TYPE       "Slot / Connector Event" 
--#SUMMARY    "Slot / Connector - holds spare device" 
--#ARGUMENTS  {} 
--#SEVERITY   INFORMATIONAL 

::= { petevts 2191113 }

-- Slot / Connector - Fault Status Deasserted 
trapSlotFaultStatusDeasserted NOTIFICATION-TYPE 
STATUS current
-- ENTERPRISE petevts 
DESCRIPTION 
 "Slot / Connector - Fault Status Deasserted" 

--#TYPE       "Slot / Connector Event" 
--#SUMMARY    "Slot / Connector - Fault Status Deasserted" 
--#ARGUMENTS  {} 
--#SEVERITY   INFORMATIONAL 

::= { petevts 2191232 }

-- Slot / Connector - Identify Status Deasserted 
trapSlotIdentifyStatusDeasserted NOTIFICATION-TYPE 
STATUS current
-- ENTERPRISE petevts 
DESCRIPTION 
 "Slot / Connector - Identify Status Deasserted" 

--#TYPE       "Slot / Connector Event" 
--#SUMMARY    "Slot / Connector - Identify Status Deasserted" 
--#ARGUMENTS  {} 
--#SEVERITY   INFORMATIONAL 

::= { petevts 2191233 }

-- Slot / Connector - Device Removed 
trapSlotDeviceRemoved NOTIFICATION-TYPE 
STATUS current
-- ENTERPRISE petevts 
DESCRIPTION 
 "Slot / Connector - Device Uninstalled/Removed" 

--#TYPE       "Slot / Connector Event" 
--#SUMMARY    "Slot / Connector - Device Uninstalled/Removed" 
--#ARGUMENTS  {} 
--#SEVERITY   INFORMATIONAL 

::= { petevts 2191234 }

-- Slot / Connector - Not Ready for Device Installation 
trapSlotNotReadyForDeviceInstallation NOTIFICATION-TYPE 
STATUS current
-- ENTERPRISE petevts 
DESCRIPTION 
 "Slot / Connector - Not Ready for Device Installation. Typically, this means that the slot power is on" 

--#TYPE       "Slot / Connector Event" 
--#SUMMARY    "Slot / Connector - Not Ready for Device Installation" 
--#ARGUMENTS  {} 
--#SEVERITY   INFORMATIONAL 

::= { petevts 2191235 }

-- Slot / Connector - Not Ready for Device Removal 
trapSlotNotReadyForDeviceRemoval NOTIFICATION-TYPE 
STATUS current
-- ENTERPRISE petevts 
DESCRIPTION 
 "Slot / Connector - Not Ready for Device Removal. Typically, this means that the slot power is on" 

--#TYPE       "Slot / Connector Event" 
--#SUMMARY    "Slot / Connector - Ready for Device Removal" 
--#ARGUMENTS  {} 
--#SEVERITY   INFORMATIONAL 

::= { petevts 2191236 }

-- Slot / Connector - Slot Power is On 
trapSlotPowerIsOn NOTIFICATION-TYPE 
STATUS current
-- ENTERPRISE petevts 
DESCRIPTION 
 "Slot / Connector - Slot Power is On" 

--#TYPE       "Slot / Connector Event" 
--#SUMMARY    "Slot / Connector - Slot Power is On" 
--#ARGUMENTS  {} 
--#SEVERITY   INFORMATIONAL 

::= { petevts 2191237 }

-- Slot / Connector - Device Removal Request Processed 
trapSlotDeviceRemovalRequestProcessed NOTIFICATION-TYPE 
STATUS current
-- ENTERPRISE petevts 
DESCRIPTION 
 "Slot / Connector - Device Removal Request Processed" 

--#TYPE       "Slot / Connector Event" 
--#SUMMARY    "Slot / Connector - Device Removal Request Processed" 
--#ARGUMENTS  {} 
--#SEVERITY   INFORMATIONAL 

::= { petevts 2191238 }

-- Slot / Connector - Interlock Deasserted 
trapSlotInterlockDeasserted NOTIFICATION-TYPE 
STATUS current
-- ENTERPRISE petevts 
DESCRIPTION 
 "Slot / Connector - Interlock Deasserted" 

--#TYPE       "Slot / Connector Event" 
--#SUMMARY    "Slot / Connector - Interlock Deasserted" 
--#ARGUMENTS  {} 
--#SEVERITY   INFORMATIONAL 

::= { petevts 2191239 }

-- Slot / Connector - Enabled 
trapSlotEnabled NOTIFICATION-TYPE 
STATUS current
-- ENTERPRISE petevts 
DESCRIPTION 
 "Slot / Connector - Enabled" 

--#TYPE       "Slot / Connector Event" 
--#SUMMARY    "Slot / Connector - Enabled" 
--#ARGUMENTS  {} 
--#SEVERITY   INFORMATIONAL 

::= { petevts 2191240 }

-- Slot / Connector - frees spare device 
trapSlotFreesSpareDevice NOTIFICATION-TYPE 
STATUS current
-- ENTERPRISE petevts 
DESCRIPTION 
 "Slot / Connector - frees spare device" 

--#TYPE       "Slot / Connector Event" 
--#SUMMARY    "Slot / Connector - frees spare device" 
--#ARGUMENTS  {} 
--#SEVERITY   INFORMATIONAL 

::= { petevts 2191241 }

-- ********************************************** 
-- *		System ACPI Power State			* 
-- ********************************************** 
-- System ACPI Power State - S0 / G0 working 
trapACPIStateS0Working NOTIFICATION-TYPE 
STATUS current
-- ENTERPRISE petevts 
DESCRIPTION 
 "System ACPI Power State - S0 / G0 - Working" 

--#TYPE       "System ACPI Power State Event" 
--#SUMMARY    "System ACPI Power State - S0 / G0 " 
--#ARGUMENTS  {} 
--#SEVERITY   INFORMATIONAL 

::= { petevts 2256640 }

-- System ACPI Power State - S1 
trapACPIStateS1 NOTIFICATION-TYPE 
STATUS current
-- ENTERPRISE petevts 
DESCRIPTION 
 "System ACPI Power State - S1 - sleeping with system h/w & processor context maintained" 

--#TYPE       "System ACPI Power State Event" 
--#SUMMARY    "System ACPI Power State - S1" 
--#ARGUMENTS  {} 
--#SEVERITY   INFORMATIONAL 

::= { petevts 2256641 }

-- System ACPI Power State - S2  
trapACPIStateS2 NOTIFICATION-TYPE 
STATUS current
-- ENTERPRISE petevts 
DESCRIPTION 
 "System ACPI Power State - S2 sleeping, processor context lost" 

--#TYPE       "System ACPI Power State Event" 
--#SUMMARY    "System ACPI Power State - S2 " 
--#ARGUMENTS  {} 
--#SEVERITY   INFORMATIONAL 

::= { petevts 2256642 }

-- System ACPI Power State - S3 
trapACPIStateS3 NOTIFICATION-TYPE 
STATUS current
-- ENTERPRISE petevts 
DESCRIPTION 
 "System ACPI Power State - S3" 

--#TYPE       "System ACPI Power State Event" 
--#SUMMARY    "System ACPI Power State - S3 - sleeping, processor & h/w context lost, memory retained" 
--#ARGUMENTS  {} 
--#SEVERITY   INFORMATIONAL 

::= { petevts 2256643 }

-- System ACPI Power State - S4 
trapACPIStateS4 NOTIFICATION-TYPE 
STATUS current
-- ENTERPRISE petevts 
DESCRIPTION 
 "System ACPI Power State - S4 - non-volatile sleep / suspend-to disk" 

--#TYPE       "System ACPI Power State Event" 
--#SUMMARY    "System ACPI Power State - S4" 
--#ARGUMENTS  {} 
--#SEVERITY   INFORMATIONAL 

::= { petevts 2256644 }

-- System ACPI Power State - S5 / G2 
trapACPIStateS5 NOTIFICATION-TYPE 
STATUS current
-- ENTERPRISE petevts 
DESCRIPTION 
 "System ACPI Power State - S5 / G2 - soft-off" 

--#TYPE       "System ACPI Power State Event" 
--#SUMMARY    "System ACPI Power State - S5 / G2" 
--#ARGUMENTS  {} 
--#SEVERITY   INFORMATIONAL 

::= { petevts 2256645 }

-- System ACPI Power State - S4 / S5 soft-off 
trapACPIStateS4OrS5SoftOff NOTIFICATION-TYPE 
STATUS current
-- ENTERPRISE petevts 
DESCRIPTION 
 "System ACPI Power State - S4 / S5 soft-off, particular S4 / S5 state cannot be determi" 

--#TYPE       "System ACPI Power State Event" 
--#SUMMARY    "System ACPI Power State - S4 / S5 soft-off" 
--#ARGUMENTS  {} 
--#SEVERITY   INFORMATIONAL 

::= { petevts 2256646 }

-- System ACPI Power State - G3 
trapACPIStateG3 NOTIFICATION-TYPE 
STATUS current
-- ENTERPRISE petevts 
DESCRIPTION 
 "System ACPI Power State - G3 - Mechanical Off" 

--#TYPE       "System ACPI Power State Event" 
--#SUMMARY    "System ACPI Power State - G3" 
--#ARGUMENTS  {} 
--#SEVERITY   INFORMATIONAL 

::= { petevts 2256647 }

-- System ACPI Power State - Sleeping in an S1, S2, or S3 states 
trapACPISleepingInUnknownState NOTIFICATION-TYPE 
STATUS current
-- ENTERPRISE petevts 
DESCRIPTION 
 "System ACPI Power State - Sleeping in an S1, S2, or S3 states" 

--#TYPE       "System ACPI Power State Event" 
--#SUMMARY    "System ACPI Power State - Sleeping in an S1, S2, or S3 states" 
--#ARGUMENTS  {} 
--#SEVERITY   INFORMATIONAL 

::= { petevts 2256648 }

-- System ACPI Power State - G1  
trapACPIStateG1 NOTIFICATION-TYPE 
STATUS current
-- ENTERPRISE petevts 
DESCRIPTION 
 "System ACPI Power State - G1 - sleeping (S1-S4 state cannot be determined)" 

--#TYPE       "System ACPI Power State Event" 
--#SUMMARY    "System ACPI Power State - G1" 
--#ARGUMENTS  {} 
--#SEVERITY   INFORMATIONAL 

::= { petevts 2256649 }

-- System ACPI Power State - S5 entered by override 
trapACPIStateS5ByOverride NOTIFICATION-TYPE 
STATUS current
-- ENTERPRISE petevts 
DESCRIPTION 
 "System ACPI Power State - S5 entered by override" 

--#TYPE       "System ACPI Power State Event" 
--#SUMMARY    "System ACPI Power State - S5 entered by override" 
--#ARGUMENTS  {} 
--#SEVERITY   INFORMATIONAL 

::= { petevts 2256650 }

-- System ACPI Power State - Legacy ON state 
trapACPILegacyONState NOTIFICATION-TYPE 
STATUS current
-- ENTERPRISE petevts 
DESCRIPTION 
 "System ACPI Power State - Legacy ON state" 

--#TYPE       "System ACPI Power State Event" 
--#SUMMARY    "System ACPI Power State - Legacy ON state" 
--#ARGUMENTS  {} 
--#SEVERITY   INFORMATIONAL 

::= { petevts 2256651 }

-- System ACPI Power State - Legacy OFF state 
trapACPILegacyOFFState NOTIFICATION-TYPE 
STATUS current
-- ENTERPRISE petevts 
DESCRIPTION 
 "System ACPI Power State - Legacy OFF state" 

--#TYPE       "System ACPI Power State Event" 
--#SUMMARY    "System ACPI Power State - Legacy OFF state" 
--#ARGUMENTS  {} 
--#SEVERITY   INFORMATIONAL 

::= { petevts 2256652 }

-- System ACPI Power State - Unknown 
trapACPIStateUnknown NOTIFICATION-TYPE 
STATUS current
-- ENTERPRISE petevts 
DESCRIPTION 
 "System ACPI Power State - Unknown" 

--#TYPE       "System ACPI Power State Event" 
--#SUMMARY    "System ACPI Power State - Unknown" 
--#ARGUMENTS  {} 
--#SEVERITY   INFORMATIONAL 

::= { petevts 2256654 }

-- ********************************************** 
-- *		Watchdog 2			* 
-- ********************************************** 
-- Watchdog timer expired 
trapWatchdogTimerExpired NOTIFICATION-TYPE 
STATUS current
-- ENTERPRISE petevts 
DESCRIPTION  
 "Watchdog timer expired, status only (no action, no interrupt)" 

--#TYPE       "Watchdog Event" 
--#SUMMARY    "Watchdog timer expired" 
--#ARGUMENTS  {} 
--#SEVERITY   WARNING 

::= { petevts  2322176 }

-- Watchdog reset event 
trapWatchdogReset NOTIFICATION-TYPE 
STATUS current
-- ENTERPRISE petevts 
DESCRIPTION  
 "Watchdog Reset" 

--#TYPE       "Watchdog Event" 
--#SUMMARY    "Watchdog Reset" 
--#ARGUMENTS  {} 
--#SEVERITY   CRITICAL 

::= { petevts  2322177 }

-- Watchdog power down event 
trapWatchdogPowerDown NOTIFICATION-TYPE 
STATUS current
-- ENTERPRISE petevts 
DESCRIPTION  
 "Watchdog Power Down" 

--#TYPE       "Watchdog Event" 
--#SUMMARY    "Watchdog Power Down" 
--#ARGUMENTS  {} 
--#SEVERITY   CRITICAL 

::= { petevts  2322178 }

-- Watchdog power cycle event 
trapWatchdogPowerCycle NOTIFICATION-TYPE 
STATUS current
-- ENTERPRISE petevts 
DESCRIPTION  
 "Watchdog Power Cycle" 

--#TYPE       "Watchdog Event" 
--#SUMMARY    "Watchdog Power cycle" 
--#ARGUMENTS  {} 
--#SEVERITY   WARNING 

::= { petevts 2322179 }

-- Watchdog Timer interrupt 
trapWatchdogTimerInterrupt NOTIFICATION-TYPE 
STATUS current
-- ENTERPRISE petevts 
DESCRIPTION  
 "Watchdog Timer interrupt" 

--#TYPE       "Watchdog Event" 
--#SUMMARY    "Watchdog Timer interrupt" 
--#ARGUMENTS  {} 
--#SEVERITY   INFORMATIONAL 

::= { petevts 2322184 }

-- Watchdog timer Reset 
trapWatchdogTimerExpiredDeasserted NOTIFICATION-TYPE 
STATUS current
-- ENTERPRISE petevts 
DESCRIPTION  
 "Watchdog timer Reset" 

--#TYPE       "Watchdog Event" 
--#SUMMARY    "Watchdog timer reset" 
--#ARGUMENTS  {} 
--#SEVERITY   WARNING 

::= { petevts  2322304 }

-- Watchdog reset event Deasserted 
trapWatchdogResetDeasserted NOTIFICATION-TYPE 
STATUS current
-- ENTERPRISE petevts 
DESCRIPTION  
 "Watchdog Reset Deasserted" 

--#TYPE       "Watchdog Event" 
--#SUMMARY    "Watchdog Reset Deasserted" 
--#ARGUMENTS  {} 
--#SEVERITY   CRITICAL 

::= { petevts  2322305 }

-- Watchdog power down event Deasserted 
trapWatchdogPowerDownDeasserted NOTIFICATION-TYPE 
STATUS current
-- ENTERPRISE petevts 
DESCRIPTION  
 "Watchdog Power Down Deasserted" 

--#TYPE       "Watchdog Event" 
--#SUMMARY    "Watchdog Power Down Deasserted" 
--#ARGUMENTS  {} 
--#SEVERITY   CRITICAL 

::= { petevts  2322306 }

-- Watchdog power cycle event Deasserted 
trapWatchdogPowerCycleDeasserted NOTIFICATION-TYPE 
STATUS current
-- ENTERPRISE petevts 
DESCRIPTION  
 "Watchdog Power Cycle Deasserted" 

--#TYPE       "Watchdog Event" 
--#SUMMARY    "Watchdog Power cycle Deasserted" 
--#ARGUMENTS  {} 
--#SEVERITY   WARNING 

::= { petevts 2322307 }

-- Watchdog Timer interrupt Deasserted 
trapWatchdogTimerInterruptDeasserted NOTIFICATION-TYPE 
STATUS current
-- ENTERPRISE petevts 
DESCRIPTION  
 "Watchdog Timer interrupt Deasserted" 

--#TYPE       "Watchdog Event" 
--#SUMMARY    "Watchdog Timer interrupt Deasserted" 
--#ARGUMENTS  {} 
--#SEVERITY   INFORMATIONAL 

::= { petevts 2322312 }

-- ********************************************** 
-- *		Platform Alert			* 
-- ********************************************** 
-- Platform Alert - platform generated page 
trapPlatformGeneratedPage NOTIFICATION-TYPE 
STATUS current
-- ENTERPRISE petevts 
DESCRIPTION  
 "Platform Alert - platform generated page" 

--#TYPE       "Platform Alert Event" 
--#SUMMARY    "Platform Alert- platform generated page" 
--#ARGUMENTS  {} 
--#SEVERITY   INFORMATIONAL 

::= { petevts 2387712 }

-- Platform Alert platform generated LAN alert 
trapPlatformGeneratedLANAlert NOTIFICATION-TYPE 
STATUS current
-- ENTERPRISE petevts 
DESCRIPTION  
 "Platform Alert - platform generated LAN alert" 

--#TYPE       "Platform Alert Event" 
--#SUMMARY    "Platform Alert- platform generated LAN alert" 
--#ARGUMENTS  {} 
--#SEVERITY   INFORMATIONAL 

::= { petevts 2387713 }

-- Platform Alert Platform Event Trap generated 
trapPlatformPETFormatTrap NOTIFICATION-TYPE 
STATUS current
-- ENTERPRISE petevts 
DESCRIPTION  
 "Platform Alert - Platform Event Trap generated" 

--#TYPE       "Platform Alert Event" 
--#SUMMARY    "Platform Alert-  Platform Event Trap generated (formatted per IPMI PET specification)" 
--#ARGUMENTS  {} 
--#SEVERITY   INFORMATIONAL 

::= { petevts 2387714 }

-- Platform Alert platform generated SNMP trap, OEM format 
trapPlatformOEMFormatTrap NOTIFICATION-TYPE 
STATUS current
-- ENTERPRISE petevts 
DESCRIPTION  
 "Platform Alert - platform generated SNMP trap, OEM format" 

--#TYPE       "Platform Alert Event" 
--#SUMMARY    "Platform Alert- platform generated SNMP trap, OEM format" 
--#ARGUMENTS  {} 
--#SEVERITY   INFORMATIONAL 

::= { petevts 2387715 }

-- ********************************************** 
-- *		Entity Presence			* 
-- ********************************************** 
-- A device is present or has been removed 
trapEntityPresenceDeviceRemovedOrAbsent NOTIFICATION-TYPE 
STATUS current
-- ENTERPRISE petevts 
DESCRIPTION  
 "A device is absent or has been removed." 

--#TYPE       "Entity Presence Event" 
--#SUMMARY    "A device is absent or has been removed." 
--#ARGUMENTS  {} 
--#SEVERITY   CRITICAL 

::= { petevts 2426880 }

-- A device is present or has been inserted 
trapEntityPresenceDeviceInsertedOrPresent NOTIFICATION-TYPE 
STATUS current
-- ENTERPRISE petevts 
DESCRIPTION  
 "A device is present or has been inserted." 

--#TYPE       "Entity Presence Event" 
--#SUMMARY    "A device is present or has been inserted." 
--#ARGUMENTS  {} 
--#SEVERITY   INFORMATIONAL 

::= { petevts 2426881 }

-- Entity Present 
trapEntityPresent NOTIFICATION-TYPE 
STATUS current
-- ENTERPRISE petevts 
DESCRIPTION  
 "The Entity identified by the Entity ID for the sensor is present." 

--#TYPE       "Entity Presence Event" 
--#SUMMARY    "Entity Present" 
--#ARGUMENTS  {} 
--#SEVERITY   INFORMATIONAL 

::= { petevts 2453248 }

-- Entity Absent. 
trapEntityAbsent NOTIFICATION-TYPE 
STATUS current
-- ENTERPRISE petevts 
DESCRIPTION  
 "The Entity identified by the Entity ID for the sensor is Absent." 

--#TYPE       "Entity Presence Event" 
--#SUMMARY    "Entity Absent." 
--#ARGUMENTS  {} 
--#SEVERITY   INFORMATIONAL 

::= { petevts 2453249 }

 -- Entity Disabled.. 
trapEntityDisabled NOTIFICATION-TYPE 
STATUS current
-- ENTERPRISE petevts 
DESCRIPTION  
 "The Entity identified by the Entity ID for the sensor is Disabled." 

--#TYPE       "Entity Presence Event" 
--#SUMMARY    "Entity Disabled." 
--#ARGUMENTS  {} 
--#SEVERITY   INFORMATIONAL 

::= { petevts 2453250 }
 
 
-- ********************************************** 
-- *		Monitor ASIC / IC			* 
-- ********************************************** 
-- Monitor ASIC / IC Failure Deasserted 
trapMonitoASICFailureDeasserted NOTIFICATION-TYPE 
STATUS current
-- ENTERPRISE petevts 
DESCRIPTION  
 "Monitor ASIC / IC Failure Deasserted" 

--#TYPE       "Monitor ASIC / IC Event" 
--#SUMMARY    "Monitor ASIC / IC Failure Deasserted" 
--#ARGUMENTS  {} 
--#SEVERITY   INFORMATIONAL 

::= { petevts 2491392 }

-- Monitor ASIC / IC Failure Asserted 
trapMonitoASICFailureAsserted NOTIFICATION-TYPE 
STATUS current
-- ENTERPRISE petevts 
DESCRIPTION  
 "Monitor ASIC / IC Failure Asserted" 

--#TYPE       "Monitor ASIC / IC Event" 
--#SUMMARY    "Monitor ASIC / IC Failure Asserted" 
--#ARGUMENTS  {} 
--#SEVERITY   MAJOR 

::= { petevts 2491393 }

-- ********************************************** 
-- *		Management Subsystem Health			* 
-- ********************************************** 
-- Sensor access degraded or unavailable 
trapSensorAccessDegradedOrUnavailable NOTIFICATION-TYPE 
STATUS current
-- ENTERPRISE petevts 
DESCRIPTION  
 "Sensor access degraded or unavailable" 

--#TYPE       "Management Subsystem Health Event" 
--#SUMMARY    "Sensor access degraded or unavailable" 
--#ARGUMENTS  {} 
--#SEVERITY   MAJOR 

::= { petevts 2649856 }

-- Controller access degraded or unavailable 
trapControllerAccessDegradedOrUnavailable NOTIFICATION-TYPE 
STATUS current
-- ENTERPRISE petevts 
DESCRIPTION  
 "Controller access degraded or unavailable" 

--#TYPE       "Management Subsystem Health Event" 
--#SUMMARY    "Controller access degraded or unavailable" 
--#ARGUMENTS  {} 
--#SEVERITY   MAJOR 

::= { petevts 2649857 }

-- Management controller off-line 
trapManagementControllerOffline NOTIFICATION-TYPE 
STATUS current
-- ENTERPRISE petevts 
DESCRIPTION  
 "Management controller off-line" 

--#TYPE       "Management Subsystem Health Event" 
--#SUMMARY    "Management controller off-line" 
--#ARGUMENTS  {} 
--#SEVERITY   MAJOR 

::= { petevts 2649858 }

-- Management controller Unavailable 
trapManagementControllerUnavailable NOTIFICATION-TYPE 
STATUS current
-- ENTERPRISE petevts 
DESCRIPTION  
 "Management controller Unavailable" 

--#TYPE       "Management Subsystem Health Event" 
--#SUMMARY    "Management controller Unavailable" 
--#ARGUMENTS  {} 
--#SEVERITY   MAJOR 

::= { petevts 2649859 }

-- Sensor failure 
trapSensorFailure NOTIFICATION-TYPE 
STATUS current
-- ENTERPRISE petevts 
DESCRIPTION  
 "Sensor failure" 

--#TYPE       "Management Subsystem Health Event" 
--#SUMMARY    "Sensor failure" 
--#ARGUMENTS  {} 
--#SEVERITY   MAJOR 

::= { petevts 2649860 }

-- FRU failure 
trapFRUFailure NOTIFICATION-TYPE 
STATUS current
-- ENTERPRISE petevts 
DESCRIPTION  
 "FRU failure" 

--#TYPE       "Management Subsystem Health Event" 
--#SUMMARY    "FRU failure" 
--#ARGUMENTS  {} 
--#SEVERITY   MAJOR 

::= { petevts 2649861 }

-- Sensor access available 
trapSensorAccessAvailable NOTIFICATION-TYPE 
STATUS current
-- ENTERPRISE petevts 
DESCRIPTION  
 "Sensor access Available" 

--#TYPE       "Management Subsystem Health Event" 
--#SUMMARY    "Sensor access Available" 
--#ARGUMENTS  {} 
--#SEVERITY   INFORMATIONAL 

::= { petevts 2649984 }

-- Controller access Available 
trapControllerAccessAvailable NOTIFICATION-TYPE 
STATUS current
-- ENTERPRISE petevts 
DESCRIPTION  
 "Controller access Available" 

--#TYPE       "Management Subsystem Health Event" 
--#SUMMARY    "Controller access Available" 
--#ARGUMENTS  {} 
--#SEVERITY   INFORMATIONAL 

::= { petevts 2649985 }

-- Management controller online 
trapManagementControllerOnline NOTIFICATION-TYPE 
STATUS current
-- ENTERPRISE petevts 
DESCRIPTION  
 "Management controller online" 

--#TYPE       "Management Subsystem Health Event" 
--#SUMMARY    "Management controller online" 
--#ARGUMENTS  {} 
--#SEVERITY   INFORMATIONAL 

::= { petevts 2649986 }

-- Management controller Available 
trapManagementControllerAvailable NOTIFICATION-TYPE 
STATUS current
-- ENTERPRISE petevts 
DESCRIPTION  
 "Management controller Available" 

--#TYPE       "Management Subsystem Health Event" 
--#SUMMARY    "Management controller Available" 
--#ARGUMENTS  {} 
--#SEVERITY   INFORMATIONAL 

::= { petevts 2649987 }

-- Sensor failure Deasserted 
trapSensorFailureDeasserted NOTIFICATION-TYPE 
STATUS current
-- ENTERPRISE petevts 
DESCRIPTION  
 "Sensor failure Deasserted" 

--#TYPE       "Management Subsystem Health Event" 
--#SUMMARY    "Sensor failure Deasserted" 
--#ARGUMENTS  {} 
--#SEVERITY   INFORMATIONAL 

::= { petevts 2649988 }

-- FRU failure Deasserted 
trapFRUFailureDeasserted NOTIFICATION-TYPE 
STATUS current
-- ENTERPRISE petevts 
DESCRIPTION  
 "FRU failure Deasserted" 

--#TYPE       "Management Subsystem Health Event" 
--#SUMMARY    "FRU failure Deasserted" 
--#ARGUMENTS  {} 
--#SEVERITY   INFORMATIONAL 

::= { petevts 2649989 }

-- ********************************************** 
-- *		Battery			* 
-- ********************************************** 

-- Battery low 
trapBatteryLowAssert NOTIFICATION-TYPE 
STATUS current
-- ENTERPRISE petevts 
DESCRIPTION  
 "Battery low" 

--#TYPE       "Battery Event" 
--#SUMMARY    "Battery low" 
--#ARGUMENTS  {} 
--#SEVERITY   WARNING 

::= { petevts 2715392 }

-- Battery failed 
trapBatteryFailed NOTIFICATION-TYPE 
STATUS current
-- ENTERPRISE petevts 
DESCRIPTION  
 "Battery Failed" 

--#TYPE       "Battery Event" 
--#SUMMARY    "Battery Failed" 
--#ARGUMENTS  {} 
--#SEVERITY   CRITICAL 

::= { petevts 2715393 }

-- Battery presence detected 
trapBatteryPresenceDetected NOTIFICATION-TYPE 
STATUS current
-- ENTERPRISE petevts 
DESCRIPTION  
 "Battery presence detected" 

--#TYPE       "Battery Event" 
--#SUMMARY    "Battery presence detected" 
--#ARGUMENTS  {} 
--#SEVERITY   INFORMATIONAL 

::= { petevts 2715394 }

-- ********************************************** 
-- *		Session Audit			* 
-- ********************************************** 

-- Session Activated 
trapSessionActivated NOTIFICATION-TYPE 
STATUS current
-- ENTERPRISE petevts 
DESCRIPTION  
 "Session Activated" 

--#TYPE       "Session Audit Event" 
--#SUMMARY    "Session Activated" 
--#ARGUMENTS  {} 
--#SEVERITY   INFORMATIONAL 

::= { petevts 2780928 }

-- Session Deactivated 
trapSessionDeactivated NOTIFICATION-TYPE 
STATUS current
-- ENTERPRISE petevts 
DESCRIPTION  
 "Session Deactivated" 

--#TYPE       "Session Audit Event" 
--#SUMMARY    "Session Deactivated" 
--#ARGUMENTS  {} 
--#SEVERITY   WARNING 

::= { petevts 2780929 }

-- Session Invalid Username or Password 
trapSessionInvalidUsernameOrPassword NOTIFICATION-TYPE 
STATUS current
-- ENTERPRISE petevts 
DESCRIPTION  
 "Session Invalid Username or Password" 

--#TYPE       "Session Audit Event" 
--#SUMMARY    "Session Invalid Username or Password" 
--#ARGUMENTS  {} 
--#SEVERITY   WARNING 

::= { petevts 2780930 }

-- Session Invalid password disable 
trapSessionUserAccessDisabled NOTIFICATION-TYPE 
STATUS current
-- ENTERPRISE petevts 
DESCRIPTION  
 "A user's access has been disabled due to a series of bad password attempts" 

--#TYPE       "Session Audit Event" 
--#SUMMARY    "Session Invalid password disable" 
--#ARGUMENTS  {} 
--#SEVERITY   WARNING 

::= { petevts 2780931 }

-- ********************************************** 
-- *		Version Change			* 
-- ********************************************** 

-- Hardware Version change detected 
trapHardwareVersionChangeDetected NOTIFICATION-TYPE 
STATUS current
-- ENTERPRISE petevts 
DESCRIPTION  
 "Hardware Version change detected with associated Entity" 

--#TYPE       "Version Change Event" 
--#SUMMARY    "Hardware Version change detected" 
--#ARGUMENTS  {} 
--#SEVERITY   INFORMATIONAL 

::= { petevts 2846464 }

-- Firmware or Software version change detected 
trapFirmwareOrSoftwareVersionChangeDetected NOTIFICATION-TYPE 
STATUS current
-- ENTERPRISE petevts 
DESCRIPTION  
 "Firmware or Software version change detected with associated Entity" 

--#TYPE       "Version Change Event" 
--#SUMMARY    "Firmware or Software version change detected" 
--#ARGUMENTS  {} 
--#SEVERITY   INFORMATIONAL 

::= { petevts 2846465 }

-- Hardware Incombabaility detected 
trapHardwareVersionIncombabailityDetected NOTIFICATION-TYPE 
STATUS current
-- ENTERPRISE petevts 
DESCRIPTION  
 "Hardware Incombabaility detected with associated Entity" 

--#TYPE       "Version Change Event" 
--#SUMMARY    "Hardware Incombabaility detected" 
--#ARGUMENTS  {} 
--#SEVERITY   INFORMATIONAL 

::= { petevts 2846466 }

-- Firmware Or Software Version Incompatibility detected 
trapFirmwareOrSoftwareVersionIncompatibilityDetected NOTIFICATION-TYPE 
STATUS current
-- ENTERPRISE petevts 
DESCRIPTION  
 "Firmware Or Software Version Incompatibility detected with associated Entity" 

--#TYPE       "Version Change Event" 
--#SUMMARY    "Firmware Or SoftwareVersion Incompatibility detected" 
--#ARGUMENTS  {} 
--#SEVERITY   INFORMATIONAL 

::= { petevts 2846467 }

-- Entity is of an invalid or unsupported hardware version 
trapEntityInvalidOrUnsupportedHardware  NOTIFICATION-TYPE 
STATUS current
-- ENTERPRISE petevts 
DESCRIPTION  
 "Entity is of an invalid or unsupported hardware version" 

--#TYPE       "Version Change Event" 
--#SUMMARY    "Entity is of an invalid or unsupported hardware version" 
--#ARGUMENTS  {} 
--#SEVERITY   INFORMATIONAL 

::= { petevts 2846468 }

-- Entity contains an invalid or unsupported firmware or software version 
trapEntityInvalidOrUnsupportedSwOrFw NOTIFICATION-TYPE 
STATUS current
-- ENTERPRISE petevts 
DESCRIPTION  
 "Entity contains an invalid or unsupported firmware or software version" 

--#TYPE       "Version Change Event" 
--#SUMMARY    "Entity contains an invalid or unsupported firmware or software version" 
--#ARGUMENTS  {} 
--#SEVERITY   INFORMATIONAL 

::= { petevts 2846469 }

-- Hardware Change detected with associated Entity was successful 
trapHardwareChangeSuccessful NOTIFICATION-TYPE 
STATUS current
-- ENTERPRISE petevts 
DESCRIPTION  
 "Hardware Change detected with associated Entity was successful" 

--#TYPE       "Version Change Event" 
--#SUMMARY    "Hardware Change detected with associated Entity was successful" 
--#ARGUMENTS  {} 
--#SEVERITY   INFORMATIONAL 

::= { petevts 2846470 }

-- Software or F/W Change detected with associated Entity was successful. 
trapSwOrFwChangeSuccessful NOTIFICATION-TYPE 
STATUS current
-- ENTERPRISE petevts 
DESCRIPTION  
 "Software or F/W Change detected with associated Entity was successful." 

--#TYPE       "Version Change Event" 
--#SUMMARY    "Software or F/W Change detected with associated Entity was successful." 
--#ARGUMENTS  {} 
--#SEVERITY   INFORMATIONAL 

::= { petevts 2846471 }
 
 -- Hardware Change detected with associated Entity was not successful 
trapHardwareChangeNotSuccessful NOTIFICATION-TYPE 
STATUS current
-- ENTERPRISE petevts 
DESCRIPTION  
 "Hardware Change detected with associated Entity was not successful" 

--#TYPE       "Version Change Event" 
--#SUMMARY    "Hardware Change detected with associated Entity was not successful" 
--#ARGUMENTS  {} 
--#SEVERITY   INFORMATIONAL 

::= { petevts 2846598 }

-- Software or F/W Change detected with associated Entity was not successful. 
trapSwOrFwChangeNotSuccessful NOTIFICATION-TYPE 
STATUS current
-- ENTERPRISE petevts 
DESCRIPTION  
 "Software or F/W Change detected with associated Entity was not successful." 

--#TYPE       "Version Change Event" 
--#SUMMARY    "Software or F/W Change detected with associated Entity was not successful." 
--#ARGUMENTS  {} 
--#SEVERITY   INFORMATIONAL 

::= { petevts 2846599 }

-- ********************************************** 
-- *		FRU State			* 
-- ********************************************** 

-- FRU Not Installed 
trapFRUNotInstalled NOTIFICATION-TYPE 
STATUS current
-- ENTERPRISE petevts 
DESCRIPTION  
 "FRU Not Installed" 

--#TYPE       "FRU State Event" 
--#SUMMARY    "FRU Not Installed" 
--#ARGUMENTS  {} 
--#SEVERITY   INFORMATIONAL 

::= { petevts 2912000 }
 
 -- FRU Inactive 
trapFRUInactive NOTIFICATION-TYPE 
STATUS current
-- ENTERPRISE petevts 
DESCRIPTION  
 "FRU Inactive" 

--#TYPE       "FRU State Event" 
--#SUMMARY    "FRU Inactive" 
--#ARGUMENTS  {} 
--#SEVERITY   INFORMATIONAL 

::= { petevts 2912001 }
 
 -- FRU Activation Requested 
trapFRUActivationRequested NOTIFICATION-TYPE 
STATUS current
-- ENTERPRISE petevts 
DESCRIPTION  
 "FRU Activation Requested" 

--#TYPE       "FRU State Event" 
--#SUMMARY    "FRU Activation Requested" 
--#ARGUMENTS  {} 
--#SEVERITY   INFORMATIONAL 

::= { petevts 2912002 }
 
 -- FRU Not Installed 
trapFRUActivationInProgress NOTIFICATION-TYPE 
STATUS current
-- ENTERPRISE petevts 
DESCRIPTION  
 "FRU Activation In Progress" 

--#TYPE       "FRU State Event" 
--#SUMMARY    "FRU Activation In Progress" 
--#ARGUMENTS  {} 
--#SEVERITY   INFORMATIONAL 

::= { petevts 2912003 }
 
 -- FRU Active 
trapFRUActive NOTIFICATION-TYPE 
STATUS current
-- ENTERPRISE petevts 
DESCRIPTION  
 "FRU Active" 

--#TYPE       "FRU State Event" 
--#SUMMARY    "FRU Active" 
--#ARGUMENTS  {} 
--#SEVERITY   INFORMATIONAL 

::= { petevts 2912004 }
 
 -- FRU Deactivation Requested 
trapFRUDeactivationRequested NOTIFICATION-TYPE 
STATUS current
-- ENTERPRISE petevts 
DESCRIPTION  
 "FRU Deactivation Requested" 

--#TYPE       "FRU State Event" 
--#SUMMARY    "FRU Deactivation Requested" 
--#ARGUMENTS  {} 
--#SEVERITY   INFORMATIONAL 

::= { petevts 2912005 }
 
 -- FRU Deactivation In Progress 
trapFRUDeactivationInProgress NOTIFICATION-TYPE 
STATUS current
-- ENTERPRISE petevts 
DESCRIPTION  
 "FRU Deactivation In Progress" 

--#TYPE       "FRU State Event" 
--#SUMMARY    "FRU Deactivation In Progress" 
--#ARGUMENTS  {} 
--#SEVERITY   INFORMATIONAL 

::= { petevts 2912006 }
 
 -- FRU Communication Lost 
trapFRUCommunicationLost NOTIFICATION-TYPE 
STATUS current
-- ENTERPRISE petevts 
DESCRIPTION  
 "FRU Communication Lost" 

--#TYPE       "FRU State Event" 
--#SUMMARY    "FRU Communication Lost" 
--#ARGUMENTS  {} 
--#SEVERITY   INFORMATIONAL 

::= { petevts 2912007 }

--20141021 << 
 -- MEM Status 
--cpu0 ch0
trapMemErrorCPU0CH0DIMM0 NOTIFICATION-TYPE 
STATUS current
-- ENTERPRISE petevts 
DESCRIPTION  
 "CPU0 Channel0 Dimm0 memory Error" 

::= { petevts 12873728 }

trapMemErrorCPU0CH0DIMM1 NOTIFICATION-TYPE 
STATUS current
-- ENTERPRISE petevts 
DESCRIPTION  
 "CPU0 Channel0 Dimm1 memory Error"
::= { petevts 12873729}

trapMemErrorCPU0CH0DIMM2 NOTIFICATION-TYPE 
STATUS current
-- ENTERPRISE petevts 
DESCRIPTION  
 "CPU0 Channel0 Dimm2 memory Error" 
::= { petevts 12873730}

--cpu0 ch1
trapMemErrorCPU0CH1DIMM0 NOTIFICATION-TYPE 
STATUS current
-- ENTERPRISE petevts 
DESCRIPTION  
 "CPU0 Channel1 Dimm0 memory Error" 
::= { petevts 12873732 }

trapMemErrorCPU0CH1DIMM1 NOTIFICATION-TYPE 
STATUS current
-- ENTERPRISE petevts 
DESCRIPTION  
 "CPU0 Channel1 Dimm1 memory Error" 

::= { petevts 12873733}

trapMemErrorCPU0CH1DIMM2 NOTIFICATION-TYPE 
STATUS current
-- ENTERPRISE petevts 
DESCRIPTION  
 "CPU0 Channel1 Dimm2 memory Error" 
::= { petevts 12873734}

--cpu0 ch2
trapMemErrorCPU0CH2DIMM0 NOTIFICATION-TYPE 
STATUS current
-- ENTERPRISE petevts 
DESCRIPTION  
 "CPU0 Channel2 Dimm0 memory Error" 
::= { petevts 12873736 }

trapMemErrorCPU0CH2DIMM1 NOTIFICATION-TYPE 
STATUS current
-- ENTERPRISE petevts 
DESCRIPTION  
 "CPU0 Channel2 Dimm1 memory Error" 
::= { petevts 12873737}

trapMemErrorCPU0CH2DIMM2 NOTIFICATION-TYPE 
STATUS current
-- ENTERPRISE petevts 
DESCRIPTION  
 "CPU0 Channel2 Dimm2 memory Error" 
::= { petevts 12873738}


--cpu0 ch3
trapMemErrorCPU0CH3DIMM0 NOTIFICATION-TYPE 
STATUS current
-- ENTERPRISE petevts 
DESCRIPTION  
 "CPU0 Channel3 Dimm0 memory Error" 
::= { petevts 12873740 }

trapMemErrorCPU0CH3DIMM1 NOTIFICATION-TYPE 
STATUS current
-- ENTERPRISE petevts 
DESCRIPTION  
 "CPU0 Channel3 Dimm1 memory Error" 
::= { petevts 12873741}

trapMemErrorCPU0CH3DIMM2 NOTIFICATION-TYPE 
STATUS current
-- ENTERPRISE petevts 
DESCRIPTION  
 "CPU0 Channel3 Dimm2 memory Error" 
::= { petevts 12873742}


--cpu1 ch0
trapMemErrorCPU1CH0DIMM0 NOTIFICATION-TYPE 
STATUS current
-- ENTERPRISE petevts 
DESCRIPTION  
 "CPU1 Channel0 Dimm0 memory Error" 

::= { petevts 12873744 }

trapMemErrorCPU1CH0DIMM1 NOTIFICATION-TYPE 
STATUS current
-- ENTERPRISE petevts 
DESCRIPTION  
 "CPU1 Channel0 Dimm1 memory Error"
::= { petevts 12873745}

trapMemErrorCPU1CH0DIMM2 NOTIFICATION-TYPE 
STATUS current
-- ENTERPRISE petevts 
DESCRIPTION  
 "CPU1 Channel0 Dimm2 memory Error" 
::= { petevts 12873746}

--cpu1 ch1
trapMemErrorCPU1CH1DIMM0 NOTIFICATION-TYPE 
STATUS current
-- ENTERPRISE petevts 
DESCRIPTION  
 "CPU1 Channel1 Dimm0 memory Error" 
::= { petevts 12873748 }

trapMemErrorCPU1CH1DIMM1 NOTIFICATION-TYPE 
STATUS current
-- ENTERPRISE petevts 
DESCRIPTION  
 "CPU1 Channel1 Dimm1 memory Error" 

::= { petevts 12873749}

trapMemErrorCPU1CH1DIMM2 NOTIFICATION-TYPE 
STATUS current
-- ENTERPRISE petevts 
DESCRIPTION  
 "CPU1 Channel1 Dimm2 memory Error" 
::= { petevts 12873750}

--cpu1 ch2
trapMemErrorCPU1CH2DIMM0 NOTIFICATION-TYPE 
STATUS current
-- ENTERPRISE petevts 
DESCRIPTION  
 "CPU1 Channel2 Dimm0 memory Error" 
::= { petevts 12873752 }

trapMemErrorCPU1CH2DIMM1 NOTIFICATION-TYPE 
STATUS current
-- ENTERPRISE petevts 
DESCRIPTION  
 "CPU1 Channel2 Dimm1 memory Error" 
::= { petevts 12873753}

trapMemErrorCPU1CH2DIMM2 NOTIFICATION-TYPE 
STATUS current
-- ENTERPRISE petevts 
DESCRIPTION  
 "CPU1 Channel2 Dimm2 memory Error" 
::= { petevts 12873754}


--cpu1 ch3
trapMemErrorCPU1CH3DIMM0 NOTIFICATION-TYPE 
STATUS current
-- ENTERPRISE petevts 
DESCRIPTION  
 "CPU1 Channel3 Dimm0 memory Error" 
::= { petevts 12873756 }

trapMemErrorCPU1CH3DIMM1 NOTIFICATION-TYPE 
STATUS current
-- ENTERPRISE petevts 
DESCRIPTION  
 "CPU1 Channel3 Dimm1 memory Error" 
::= { petevts 12873757}

trapMemErrorCPU1CH3DIMM2 NOTIFICATION-TYPE 
STATUS current
-- ENTERPRISE petevts 
DESCRIPTION  
 "CPU1 Channel3 Dimm2 memory Error" 
::= { petevts 12873758}

--oem cpu error
trapCPUErrorCPU0BUSORINTERCONNECTERROR NOTIFICATION-TYPE 
STATUS current
-- ENTERPRISE petevts 
DESCRIPTION  
 "CPU0 Bus and interconnect Error" 
::= { petevts 12808192}

trapCPUErrorCPU0L3TAGERROR NOTIFICATION-TYPE 
STATUS current
-- ENTERPRISE petevts 
DESCRIPTION  
 "CPU0 L3 Tag Error" 
::= { petevts 12808193}

trapCPUErrorCPU0INTERNALERROR NOTIFICATION-TYPE 
STATUS current
-- ENTERPRISE petevts 
DESCRIPTION  
 "CPU0 Internal Error" 
::= { petevts 12808194}

trapCPUErrorCPU1BUSORINTERCONNECTERROR NOTIFICATION-TYPE 
STATUS current
-- ENTERPRISE petevts 
DESCRIPTION  
 "CPU1 Bus and interconnect Error" 
::= { petevts 12808208}

trapCPUErrorCPU1L3TAGERROR NOTIFICATION-TYPE 
STATUS current
-- ENTERPRISE petevts 
DESCRIPTION  
 "CPU1 L3 Tag Error" 
::= { petevts 12808209}

trapCPUErrorCPU1INTERNALERROR NOTIFICATION-TYPE 
STATUS current
-- ENTERPRISE petevts 
DESCRIPTION  
 "CPU1 Internal Error" 
::= { petevts 12808210}

trapCPUErrorCPU2BUSORINTERCONNECTERROR NOTIFICATION-TYPE 
STATUS current
-- ENTERPRISE petevts 
DESCRIPTION  
 "CPU2 Bus and interconnect Error" 
::= { petevts 12808224}

trapCPUErrorCPU2L3TAGERROR NOTIFICATION-TYPE 
STATUS current
-- ENTERPRISE petevts 
DESCRIPTION  
 "CPU2 L3 Tag Error" 
::= { petevts 12808225}

trapCPUErrorCPU2INTERNALERROR NOTIFICATION-TYPE 
STATUS current
-- ENTERPRISE petevts 
DESCRIPTION  
 "CPU2 Internal Error" 
::= { petevts 12808226}

trapCPUErrorCPU3BUSORINTERCONNECTERROR NOTIFICATION-TYPE 
STATUS current
-- ENTERPRISE petevts 
DESCRIPTION  
 "CPU3 Bus and interconnect Error" 
::= { petevts 12808240}

trapCPUErrorCPU3L3TAGERROR NOTIFICATION-TYPE 
STATUS current
-- ENTERPRISE petevts 
DESCRIPTION  
 "CPU3 L3 Tag Error" 
::= { petevts 12808241}

trapCPUErrorCPU3INTERNALERROR NOTIFICATION-TYPE 
STATUS current
-- ENTERPRISE petevts 
DESCRIPTION  
 "CPU3 Internal Error" 
::= { petevts 12808242}
--20141021>>

-- ********************************************** 
-- *		Temperature			* 
-- ********************************************** 

-- Temperature has decreased below lower non-critical threshold 
trapUnderTemperatureWarningLow TRAP-TYPE 
ENTERPRISE petevts 
DESCRIPTION  
"Under-Temperature Warning (Lower non-critical, going low)" 

--#TYPE       "Temperature Event" 
--#SUMMARY    "Under-Temperature Warning (Lower non-critical, going low)" 
--#ARGUMENTS  {} 
--#SEVERITY   WARNING 

::= 65792 
 
-- Temperature has increased above lower non-critical threshold 
trapUnderTemperatureWarningHigh TRAP-TYPE 
ENTERPRISE petevts 
DESCRIPTION  
"Under-Temperature Warning (Lower non-critical, going high)" 

--#TYPE       "Temperature Event" 
--#SUMMARY    "Under-Temperature Warning (Lower non-critical, going high)" 
--#ARGUMENTS  {} 
--#SEVERITY   WARNING 

::= 65793 
 
-- Temperature has decreased below lower critical threshold 
trapUnderTemperatureCriticalLow TRAP-TYPE 
ENTERPRISE petevts 
DESCRIPTION  
"Critical Under-Temperature problem (Lower critical, going low)" 

--#TYPE       "Temperature Event" 
--#SUMMARY    "Under-Temperature Warning (Lower critical, going low)" 
--#ARGUMENTS  {} 
--#SEVERITY   CRITICAL 

::= 65794 
 
 -- Temperature has increased above lower critical threshold 
trapUnderTemperatureCriticalHigh TRAP-TYPE 
ENTERPRISE petevts 
DESCRIPTION  
"Critical Under-Temperature problem (Lower critical, going high)" 

--#TYPE       "Temperature Event" 
--#SUMMARY    "Under-Temperature Warning (Lower critical, going high)" 
--#ARGUMENTS  {} 
--#SEVERITY   CRITICAL 

::= 65795 
 
 -- Temperature has decreased below lower non-recoverable threshold 
trapUnderTemperatureNonRecoverableLow TRAP-TYPE 
ENTERPRISE petevts 
DESCRIPTION  
"Critical Under-Temperature problem (Lower non-recoverable, going low)" 

--#TYPE       "Temperature Event" 
--#SUMMARY    "Under-Temperature Warning (Lower non-recoverable, going low)" 
--#ARGUMENTS  {} 
--#SEVERITY   CRITICAL 

::= 65796 
 
 -- Temperature has increased above lower non-recoverable threshold 
trapUnderTemperatureNonRecoverableHigh TRAP-TYPE 
ENTERPRISE petevts 
DESCRIPTION  
"Critical Under-Temperature problem (Lower non-recoverable, going high)" 

--#TYPE       "Temperature Event" 
--#SUMMARY    "Under-Temperature Warning (Lower non-recoverable, going high)" 
--#ARGUMENTS  {} 
--#SEVERITY   CRITICAL 

::= 65797 
 
-- Temperature has decreased below Upper non-critical threshold 
trapOverTemperatureWarningLow TRAP-TYPE 
ENTERPRISE petevts 
DESCRIPTION  
"Over-Temperature Warning (Upper non-critical, going low)" 

--#TYPE       "Temperature Event" 
--#SUMMARY    "Over-Temperature Warning (Upper non-critical, going low)" 
--#ARGUMENTS  {} 
--#SEVERITY   WARNING 

::= 65798 
 
-- Temperature has increased above upper non-critical threshold. 
trapOverTemperatureWarningHigh TRAP-TYPE 
ENTERPRISE petevts 
DESCRIPTION  
"Over-Temperature Warning (Upper non-critical, going high)" 

--#TYPE       "Temperature Event" 
--#SUMMARY    "Over-Temperature Warning (Upper non-critical, going high)" 
--#ARGUMENTS  {} 
--#SEVERITY   WARNING 

::= 65799 
 
-- Temperature has decreased below Upper critical threshold 
trapOverTemperatureCriticalLow TRAP-TYPE 
ENTERPRISE petevts 
DESCRIPTION  
"Critical Over-Temperature problem (Upper critical, going low)" 

--#TYPE       "Temperature Event" 
--#SUMMARY    "Over-Temperature Warning (Upper critical, going low)" 
--#ARGUMENTS  {} 
--#SEVERITY   CRITICAL 

::= 65800 
 
 -- Temperature has increased above Upper critical threshold 
trapOverTemperatureCriticalHigh TRAP-TYPE 
ENTERPRISE petevts 
DESCRIPTION  
"Critical Over-Temperature problem (Upper critical, going high)" 

--#TYPE       "Temperature Event" 
--#SUMMARY    "Over-Temperature Warning (Upper critical, going high)" 
--#ARGUMENTS  {} 
--#SEVERITY   CRITICAL 

::= 65801 
 
 -- Temperature has decreased below Upper non-recoverable threshold 
trapOverTemperatureNonRecoverableLow TRAP-TYPE 
ENTERPRISE petevts 
DESCRIPTION  
"Critical Over-Temperature problem (Upper non-recoverable, going low)" 

--#TYPE       "Temperature Event" 
--#SUMMARY    "Over-Temperature Warning (Upper non-recoverable, going low)" 
--#ARGUMENTS  {} 
--#SEVERITY   CRITICAL 

::= 65802 
 
 -- Temperature has increased above Upper non-recoverable threshold 
trapOverTemperatureNonRecoverableHigh TRAP-TYPE 
ENTERPRISE petevts 
DESCRIPTION  
"Critical Over-Temperature problem (Upper non-recoverable, going high)" 

--#TYPE       "Temperature Event" 
--#SUMMARY    "Under-Temperature Warning (Upper non-recoverable, going high)" 
--#ARGUMENTS  {} 
--#SEVERITY   CRITICAL 

::= 65803 
 
-- Temperature decreased below lower non-critical threshold Cleared 
trapUnderTemperatureWarningLowCleared TRAP-TYPE 
ENTERPRISE petevts 
DESCRIPTION  
"Under-Temperature Warning (Lower non-critical, going low) Cleared" 

--#TYPE       "Temperature Event" 
--#SUMMARY    "Under-Temperature Warning (Lower non-critical, going low) Cleared" 
--#ARGUMENTS  {} 
--#SEVERITY   INFORMATIONAL 

::= 65920 
 
-- Temperature increased above lower non-critical threshold Cleared 
trapUnderTemperatureWarningHighCleared TRAP-TYPE 
ENTERPRISE petevts 
DESCRIPTION  
"Under-Temperature Warning (Lower non-critical, going high)Cleared" 

--#TYPE       "Temperature Event" 
--#SUMMARY    "Under-Temperature Warning (Lower non-critical, going high)Cleared" 
--#ARGUMENTS  {} 
--#SEVERITY   INFORMATIONAL 

::= 65921 
 
-- Temperature decreased below lower critical threshold Cleared 
trapUnderTemperatureCriticalLowCleared TRAP-TYPE 
ENTERPRISE petevts 
DESCRIPTION  
"Critical Under-Temperature problem (Lower critical, going low)Cleared" 

--#TYPE       "Temperature Event" 
--#SUMMARY    "Under-Temperature Warning (Lower critical, going low)Cleared" 
--#ARGUMENTS  {} 
--#SEVERITY   INFORMATIONAL 

::= 65922 
 
 -- Temperature increased above lower critical threshold Cleared 
trapUnderTemperatureCriticalHighCleared TRAP-TYPE 
ENTERPRISE petevts 
DESCRIPTION  
"Critical Under-Temperature problem (Lower critical, going high) Cleared" 

--#TYPE       "Temperature Event" 
--#SUMMARY    "Under-Temperature Warning (Lower critical, going high) Cleared" 
--#ARGUMENTS  {} 
--#SEVERITY   INFORMATIONAL 

::= 65923 
 
 -- Temperature decreased below lower non-recoverable threshold Cleared 
trapUnderTemperatureNonRecoverableLowCleared TRAP-TYPE 
ENTERPRISE petevts 
DESCRIPTION  
"Critical Under-Temperature problem (Lower non-recoverable, going low)Cleared" 

--#TYPE       "Temperature Event" 
--#SUMMARY    "Under-Temperature Warning (Lower non-recoverable, going low)Cleared" 
--#ARGUMENTS  {} 
--#SEVERITY   INFORMATIONAL 

::= 65924 
 
 -- Temperature increased above lower non-recoverable threshold Cleared 
trapUnderTemperatureNonRecoverableHighCleared TRAP-TYPE 
ENTERPRISE petevts 
DESCRIPTION  
"Critical Under-Temperature problem (Lower non-recoverable, going high) Cleared" 

--#TYPE       "Temperature Event" 
--#SUMMARY    "Under-Temperature Warning (Lower non-recoverable, going high) Cleared" 
--#ARGUMENTS  {} 
--#SEVERITY   INFORMATIONAL 

::= 65925 
 
-- Temperature decreased below Upper non-critical threshold Cleared 
trapOverTemperatureWarningLowCleared TRAP-TYPE 
ENTERPRISE petevts 
DESCRIPTION  
"Over-Temperature Warning (Upper non-critical, going low) Cleared" 

--#TYPE       "Temperature Event" 
--#SUMMARY    "Over-Temperature Warning (Upper non-critical, going low) Cleared" 
--#ARGUMENTS  {} 
--#SEVERITY   INFORMATIONAL 

::= 65926 
 
-- Temperature increased above upper non-critical threshold Cleared 
trapOverTemperatureWarningHighCleared TRAP-TYPE 
ENTERPRISE petevts 
DESCRIPTION  
"Over-Temperature Warning (Upper non-critical, going high)Cleared" 

--#TYPE       "Temperature Event" 
--#SUMMARY    "Over-Temperature Warning (Upper non-critical, going high)Cleared" 
--#ARGUMENTS  {} 
--#SEVERITY   INFORMATIONAL 

::= 65927 
 
-- Temperature decreased below Upper critical threshold Cleared 
trapOverTemperatureCriticalLowCleared TRAP-TYPE 
ENTERPRISE petevts 
DESCRIPTION  
"Critical Over-Temperature problem (Upper critical, going low) Cleared" 

--#TYPE       "Temperature Event" 
--#SUMMARY    "Over-Temperature Warning (Upper critical, going low) Cleared" 
--#ARGUMENTS  {} 
--#SEVERITY   INFORMATIONAL 

::= 65928 
 
 -- Temperature increased above Upper critical threshold Cleared 
trapOverTemperatureCriticalHighCleared TRAP-TYPE 
ENTERPRISE petevts 
DESCRIPTION  
"Critical Over-Temperature problem (Upper critical, going high)Cleared" 

--#TYPE       "Temperature Event" 
--#SUMMARY    "Over-Temperature Warning (Upper critical, going high)Cleared" 
--#ARGUMENTS  {} 
--#SEVERITY   INFORMATIONAL 

::= 65929 
 
 -- Temperature decreased below Upper non-recoverable threshold Cleared 
trapOverTemperatureNonRecoverableLowCleared TRAP-TYPE 
ENTERPRISE petevts 
DESCRIPTION  
"Critical Over-Temperature problem (Upper non-recoverable, going low)Cleared" 

--#TYPE       "Temperature Event" 
--#SUMMARY    "Over-Temperature Warning (Upper non-recoverable, going low)Cleared" 
--#ARGUMENTS  {} 
--#SEVERITY   INFORMATIONAL 

::= 65930 
 
 -- Temperature increased above Upper non-recoverable threshold Cleared 
trapOverTemperatureNonRecoverableHighCleared TRAP-TYPE 
ENTERPRISE petevts 
DESCRIPTION  
"Critical Over-Temperature problem (Upper non-recoverable, going high) Cleared" 

--#TYPE       "Temperature Event" 
--#SUMMARY    "Under-Temperature Warning (Upper non-recoverable, going high) Cleared" 
--#ARGUMENTS  {} 
--#SEVERITY   INFORMATIONAL 

::= 65931 
 
-- Generic critical temperature problem 
trapGenericCriticalTemperature TRAP-TYPE 
ENTERPRISE petevts 
DESCRIPTION  
"Generic Critical Temperature Problem (Transition to Critical from less severe)" 

--#TYPE       "Temperature Event" 
--#SUMMARY    "Generic Critical Temperature Problem (Transition to Critical from less severe)" 
--#ARGUMENTS  {} 
--#SEVERITY   CRITICAL 

::= 67330 

-- Generic temperature warning 
trapGenericTemperatureWarning TRAP-TYPE 
ENTERPRISE petevts 
DESCRIPTION  
 "Generic Temperature Warning (Transition to Warning from less severe)" 

--#TYPE	      "Temperature Event" 
--#SUMMARY    "Generic Temperature Warning (Transition to Warning from less severe)" 
--#ARGUMENTS  {} 
--#SEVERITY   WARNING 

::= 67331 
 
-- ********************************************** 
-- *		Voltage			* 
-- ********************************************** 

-- Voltage has decreased below lower non-critical threshold 
trapUnderVoltageWarningLow TRAP-TYPE 
ENTERPRISE petevts 
DESCRIPTION  
"Under-Voltage Warning (Lower non-critical, going low)" 

--#TYPE       "Voltage Event" 
--#SUMMARY    "Under-Voltage Warning (Lower non-critical, going low)" 
--#ARGUMENTS  {} 
--#SEVERITY   WARNING 

::= 131328 
 
-- Voltage has increased above lower non-critical threshold 
trapUnderVoltageWarningHigh TRAP-TYPE 
ENTERPRISE petevts 
DESCRIPTION  
"Under-Voltage Warning (Lower non-critical, going high)" 

--#TYPE       "Voltage Event" 
--#SUMMARY    "Under-Voltage Warning (Lower non-critical, going high)" 
--#ARGUMENTS  {} 
--#SEVERITY   WARNING 

::= 131329 
 
-- Voltage has decreased below lower critical threshold 
trapUnderVoltageCriticalLow TRAP-TYPE 
ENTERPRISE petevts 
DESCRIPTION  
"Critical Under-Voltage problem (Lower critical, going low)" 

--#TYPE       "Voltage Event" 
--#SUMMARY    "Under-Voltage Warning (Lower critical, going low)" 
--#ARGUMENTS  {} 
--#SEVERITY   CRITICAL 

::= 131330 
 
 -- Voltage has increased above lower critical threshold 
trapUnderVoltageCriticalHigh TRAP-TYPE 
ENTERPRISE petevts 
DESCRIPTION  
"Critical Under-Voltage problem (Lower critical, going high)" 

--#TYPE       "Voltage Event" 
--#SUMMARY    "Under-Voltage Warning (Lower critical, going high)" 
--#ARGUMENTS  {} 
--#SEVERITY   CRITICAL 

::= 131331 
 
 -- Voltage has decreased below lower non-recoverable threshold 
trapUnderVoltageNonRecoverableLow TRAP-TYPE 
ENTERPRISE petevts 
DESCRIPTION  
"Critical Under-Voltage problem (Lower non-recoverable, going low)" 

--#TYPE       "Voltage Event" 
--#SUMMARY    "Under-Voltage Warning (Lower non-recoverable, going low)" 
--#ARGUMENTS  {} 
--#SEVERITY   CRITICAL 

::= 131332 
 
 -- Voltage has increased above lower non-recoverable threshold 
trapUnderVoltageNonRecoverableHigh TRAP-TYPE 
ENTERPRISE petevts 
DESCRIPTION  
"Critical Under-Voltage problem (Lower non-recoverable, going high)" 

--#TYPE       "Voltage Event" 
--#SUMMARY    "Under-Voltage Warning (Lower non-recoverable, going high)" 
--#ARGUMENTS  {} 
--#SEVERITY   CRITICAL 

::= 131333 
 
-- Voltage has decreased below Upper non-critical threshold 
trapOverVoltageWarningLow TRAP-TYPE 
ENTERPRISE petevts 
DESCRIPTION  
"Over-Voltage Warning (Upper non-critical, going low)" 

--#TYPE       "Voltage Event" 
--#SUMMARY    "Over-Voltage Warning (Upper non-critical, going low)" 
--#ARGUMENTS  {} 
--#SEVERITY   WARNING 

::= 131334 
 
-- Voltage has increased above upper non-critical threshold. 
trapOverVoltageWarningHigh TRAP-TYPE 
ENTERPRISE petevts 
DESCRIPTION  
"Over-Voltage Warning (Upper non-critical, going high)" 

--#TYPE       "Voltage Event" 
--#SUMMARY    "Over-Voltage Warning (Upper non-critical, going high)" 
--#ARGUMENTS  {} 
--#SEVERITY   WARNING 

::= 131335 
 
-- Voltage has decreased below Upper critical threshold 
trapOverVoltageCriticalLow TRAP-TYPE 
ENTERPRISE petevts 
DESCRIPTION  
"Critical Over-Voltage problem (Upper critical, going low)" 

--#TYPE       "Voltage Event" 
--#SUMMARY    "Over-Voltage Warning (Upper critical, going low)" 
--#ARGUMENTS  {} 
--#SEVERITY   CRITICAL 

::= 131336 
 
 -- Voltage has increased above Upper critical threshold 
trapOverVoltageCriticalHigh TRAP-TYPE 
ENTERPRISE petevts 
DESCRIPTION  
"Critical Over-Voltage problem (Upper critical, going high)" 

--#TYPE       "Voltage Event" 
--#SUMMARY    "Over-Voltage Warning (Upper critical, going high)" 
--#ARGUMENTS  {} 
--#SEVERITY   CRITICAL 

::= 131337 
 
 -- Voltage has decreased below Upper non-recoverable threshold 
trapOverVoltageNonRecoverableLow TRAP-TYPE 
ENTERPRISE petevts 
DESCRIPTION  
"Critical Over-Voltage problem (Upper non-recoverable, going low)" 

--#TYPE       "Voltage Event" 
--#SUMMARY    "Over-Voltage Warning (Upper non-recoverable, going low)" 
--#ARGUMENTS  {} 
--#SEVERITY   CRITICAL 

::= 131338 
 
 -- Voltage has increased above Upper non-recoverable threshold 
trapOverVoltageNonRecoverableHigh TRAP-TYPE 
ENTERPRISE petevts 
DESCRIPTION  
"Critical Over-Voltage problem (Upper non-recoverable, going high)" 

--#TYPE       "Voltage Event" 
--#SUMMARY    "Under-Voltage Warning (Upper non-recoverable, going high)" 
--#ARGUMENTS  {} 
--#SEVERITY   CRITICAL 

::= 131339 
 
-- Voltage decreased below lower non-critical threshold Cleared 
trapUnderVoltageWarningLowCleared TRAP-TYPE 
ENTERPRISE petevts 
DESCRIPTION  
"Under-Voltage Warning (Lower non-critical, going low) Cleared" 

--#TYPE       "Voltage Event" 
--#SUMMARY    "Under-Voltage Warning (Lower non-critical, going low) Cleared" 
--#ARGUMENTS  {} 
--#SEVERITY   INFORMATIONAL 

::= 131456 
 
-- Voltage increased above lower non-critical threshold Cleared 
trapUnderVoltageWarningHighCleared TRAP-TYPE 
ENTERPRISE petevts 
DESCRIPTION  
"Under-Voltage Warning (Lower non-critical, going high)Cleared" 

--#TYPE       "Voltage Event" 
--#SUMMARY    "Under-Voltage Warning (Lower non-critical, going high)Cleared" 
--#ARGUMENTS  {} 
--#SEVERITY   INFORMATIONAL 

::= 131457 
 
-- Voltage decreased below lower critical threshold Cleared 
trapUnderVoltageCriticalLowCleared TRAP-TYPE 
ENTERPRISE petevts 
DESCRIPTION  
"Critical Under-Voltage problem (Lower critical, going low)Cleared" 

--#TYPE       "Voltage Event" 
--#SUMMARY    "Under-Voltage Warning (Lower critical, going low)Cleared" 
--#ARGUMENTS  {} 
--#SEVERITY   INFORMATIONAL 

::= 131458 
 
 -- Voltage increased above lower critical threshold Cleared 
trapUnderVoltageCriticalHighCleared TRAP-TYPE 
ENTERPRISE petevts 
DESCRIPTION  
"Critical Under-Voltage problem (Lower critical, going high) Cleared" 

--#TYPE       "Voltage Event" 
--#SUMMARY    "Under-Voltage Warning (Lower critical, going high) Cleared" 
--#ARGUMENTS  {} 
--#SEVERITY   INFORMATIONAL 

::= 131459 
 
 -- Voltage decreased below lower non-recoverable threshold Cleared 
trapUnderVoltageNonRecoverableLowCleared TRAP-TYPE 
ENTERPRISE petevts 
DESCRIPTION  
"Critical Under-Voltage problem (Lower non-recoverable, going low)Cleared" 

--#TYPE       "Voltage Event" 
--#SUMMARY    "Under-Voltage Warning (Lower non-recoverable, going low)Cleared" 
--#ARGUMENTS  {} 
--#SEVERITY   INFORMATIONAL 

::= 131460 
 
 -- Voltage increased above lower non-recoverable threshold Cleared 
trapUnderVoltageNonRecoverableHighCleared TRAP-TYPE 
ENTERPRISE petevts 
DESCRIPTION  
"Critical Under-Voltage problem (Lower non-recoverable, going high) Cleared" 

--#TYPE       "Voltage Event" 
--#SUMMARY    "Under-Voltage Warning (Lower non-recoverable, going high) Cleared" 
--#ARGUMENTS  {} 
--#SEVERITY   INFORMATIONAL 

::= 131461 
 
-- Voltage decreased below Upper non-critical threshold Cleared 
trapOverVoltageWarningLowCleared TRAP-TYPE 
ENTERPRISE petevts 
DESCRIPTION  
"Over-Voltage Warning (Upper non-critical, going low) Cleared" 

--#TYPE       "Voltage Event" 
--#SUMMARY    "Over-Voltage Warning (Upper non-critical, going low) Cleared" 
--#ARGUMENTS  {} 
--#SEVERITY   INFORMATIONAL 

::= 131462 
 
-- Voltage increased above upper non-critical threshold Cleared 
trapOverVoltageWarningHighCleared TRAP-TYPE 
ENTERPRISE petevts 
DESCRIPTION  
"Over-Voltage Warning (Upper non-critical, going high)Cleared" 

--#TYPE       "Voltage Event" 
--#SUMMARY    "Over-Voltage Warning (Upper non-critical, going high)Cleared" 
--#ARGUMENTS  {} 
--#SEVERITY   INFORMATIONAL 

::= 131463 
 
-- Voltage decreased below Upper critical threshold Cleared 
trapOverVoltageCriticalLowCleared TRAP-TYPE 
ENTERPRISE petevts 
DESCRIPTION  
"Critical Over-Voltage problem (Upper critical, going low) Cleared" 

--#TYPE       "Voltage Event" 
--#SUMMARY    "Over-Voltage Warning (Upper critical, going low) Cleared" 
--#ARGUMENTS  {} 
--#SEVERITY   INFORMATIONAL 

::= 131464 
 
 -- Voltage increased above Upper critical threshold Cleared 
trapOverVoltageCriticalHighCleared TRAP-TYPE 
ENTERPRISE petevts 
DESCRIPTION  
"Critical Over-Voltage problem (Upper critical, going high)Cleared" 

--#TYPE       "Voltage Event" 
--#SUMMARY    "Over-Voltage Warning (Upper critical, going high)Cleared" 
--#ARGUMENTS  {} 
--#SEVERITY   INFORMATIONAL 

::= 131465 
 
 -- Voltage decreased below Upper non-recoverable threshold Cleared 
trapOverVoltageNonRecoverableLowCleared TRAP-TYPE 
ENTERPRISE petevts 
DESCRIPTION  
"Critical Over-Voltage problem (Upper non-recoverable, going low)Cleared" 

--#TYPE       "Voltage Event" 
--#SUMMARY    "Over-Voltage Warning (Upper non-recoverable, going low)Cleared" 
--#ARGUMENTS  {} 
--#SEVERITY   INFORMATIONAL 

::= 131466 
 
 -- Voltage increased above Upper non-recoverable threshold Cleared 
trapOverVoltageNonRecoverableHighCleared TRAP-TYPE 
ENTERPRISE petevts 
DESCRIPTION  
"Critical Over-Voltage problem (Upper non-recoverable, going high) Cleared" 

--#TYPE       "Voltage Event" 
--#SUMMARY    "Under-Voltage Warning (Upper non-recoverable, going high) Cleared" 
--#ARGUMENTS  {} 
--#SEVERITY   INFORMATIONAL 

::= 131467 
 
-- (Discrete voltage) Critical voltage problem 
trapGenericCriticalDiscreteVoltageCleared TRAP-TYPE 
ENTERPRISE petevts 
DESCRIPTION  
 "Generic Critical Voltage Problem Cleared" 

--#TYPE       "Voltage Event" 
--#SUMMARY    "Generic Critical Voltage Problem Cleared" 
--#ARGUMENTS  {} 
--#SEVERITY   INFORMATIONAL 

::= 131840 

-- (Discrete voltage) Critical voltage problem 
trapGenericCriticalDiscreteVoltage TRAP-TYPE 
ENTERPRISE petevts 
DESCRIPTION  
 "Generic Critical Voltage Problem (Transition to Critical from less severe)" 

--#TYPE       "Voltage Event" 
--#SUMMARY    "Generic Critical Voltage Problem (Transition to Critical from less severe)" 
--#ARGUMENTS  {} 
--#SEVERITY   CRITICAL 

::= 131841 
 
-- (Discrete voltage) Critical voltage problem cleared 
trapGenericCriticalDiscreteVoltage2Cleared TRAP-TYPE 
ENTERPRISE petevts 
DESCRIPTION  
 "Generic Critical Voltage Problem Cleared(Transition to OK)" 

--#TYPE	      "Voltage Event" 
--#SUMMARY    "Generic Critical Voltage Problem Cleared(Transition to OK)" 
--#ARGUMENTS  {} 
--#SEVERITY   INFORMATIONAL 

::= 132864 
 
-- (Discrete voltage) Non-Critical voltage problem  
trapGenericNonCriticalDiscreteVoltage2 TRAP-TYPE 
ENTERPRISE petevts 
DESCRIPTION  
 "Generic Non-Critical Voltage Problem (Transition to Non-critical from OK)" 

--#TYPE	      "Voltage Event" 
--#SUMMARY    "Generic Critical Voltage Problem (Transition to Non-critical from OK)" 
--#ARGUMENTS  {} 
--#SEVERITY   WARNING 

::= 132865 
 
-- (Discrete voltage) Critical voltage problem 
trapGenericCriticalDiscreteVoltage2 TRAP-TYPE 
ENTERPRISE petevts 
DESCRIPTION  
 "Generic Critical Voltage Problem (Transition to Critical from less severe)" 

--#TYPE	      "Voltage Event" 
--#SUMMARY    "Generic Critical Voltage Problem (Transition to Critical from less severe)" 
--#ARGUMENTS  {} 
--#SEVERITY   CRITICAL 

::= 132866 

-- (Discrete voltage) Non-Critical voltage problem 
trapGenericDiscreteVoltageWarning TRAP-TYPE 
ENTERPRISE petevts 
DESCRIPTION  
 "Generic Voltage Warning (Transition to Non-Critical from less severe)" 

--#TYPE	      "Voltage Event" 
--#SUMMARY    "Generic Voltage Warning (Transition to Non-Critical from less severe)" 
--#ARGUMENTS  {} 
--#SEVERITY   WARNING 

::= 132867 

-- (Discrete voltage) Non-Critical voltage problem 
trapGenericDiscreteVoltageWarning2 TRAP-TYPE 
ENTERPRISE petevts 
DESCRIPTION  
 "Generic Voltage Warning (Transition to Non-Critical from more severe)" 

--#TYPE	      "Voltage Event" 
--#SUMMARY    "Generic Voltage Warning (Transition to Non-Critical from more severe)" 
--#ARGUMENTS  {} 
--#SEVERITY   WARNING 

::= 132868 
 
-- (Discrete voltage) Non-Recoverable voltage problem 
trapGenericDiscreteVoltageNonRecoverable TRAP-TYPE 
ENTERPRISE petevts 
DESCRIPTION  
 "Generic Voltage Warning (Transition to Non-Recoverable)" 

--#TYPE	      "Voltage Event" 
--#SUMMARY    "Generic Voltage Warning (Transition to Non-Recoverable)" 
--#ARGUMENTS  {} 
--#SEVERITY   CRITICAL 

::= 132869 
 
 -- (Discrete voltage) Non-Recoverable voltage problem 
trapGenericDiscreteVoltageMonitor TRAP-TYPE 
ENTERPRISE petevts 
DESCRIPTION  
 "Generic Discrete Voltage  (Monitor)" 

--#TYPE	      "Voltage Event" 
--#SUMMARY    "Generic Discrete Voltage (Monitor)" 
--#ARGUMENTS  {} 
--#SEVERITY   INFORMATIONAL 

::= 132870 
 
  -- (Discrete voltage) Non-Recoverable voltage problem 
trapGenericDiscreteVoltageInformational TRAP-TYPE 
ENTERPRISE petevts 
DESCRIPTION  
 "Generic Discrete Voltage  (Informational)" 

--#TYPE	      "Voltage Event" 
--#SUMMARY    "Generic Discrete Voltage (Informational)" 
--#ARGUMENTS  {} 
--#SEVERITY   INFORMATIONAL 

::= 132871 
 
-- ********************************************** 
-- *		Current			* 
-- ********************************************** 

-- Current has decreased below lower non-critical threshold 
trapUnderCurrentWarningLow TRAP-TYPE 
ENTERPRISE petevts 
DESCRIPTION  
"Under-Current Warning (Lower non-critical, going low)" 

--#TYPE       "Current Event" 
--#SUMMARY    "Under-Current Warning (Lower non-critical, going low)" 
--#ARGUMENTS  {} 
--#SEVERITY   WARNING 

::= 196864 
 
-- Current has increased above lower non-critical threshold 
trapUnderCurrentWarningHigh TRAP-TYPE 
ENTERPRISE petevts 
DESCRIPTION  
"Under-Current Warning (Lower non-critical, going high)" 

--#TYPE       "Current Event" 
--#SUMMARY    "Under-Current Warning (Lower non-critical, going high)" 
--#ARGUMENTS  {} 
--#SEVERITY   WARNING 

::= 196865 
 
-- Current has decreased below lower critical threshold 
trapUnderCurrentCriticalLow TRAP-TYPE 
ENTERPRISE petevts 
DESCRIPTION  
"Critical Under-Current problem (Lower critical, going low)" 

--#TYPE       "Current Event" 
--#SUMMARY    "Under-Current Warning (Lower critical, going low)" 
--#ARGUMENTS  {} 
--#SEVERITY   CRITICAL 

::= 196866 
 
 -- Current has increased above lower critical threshold 
trapUnderCurrentCriticalHigh TRAP-TYPE 
ENTERPRISE petevts 
DESCRIPTION  
"Critical Under-Current problem (Lower critical, going high)" 

--#TYPE       "Current Event" 
--#SUMMARY    "Under-Current Warning (Lower critical, going high)" 
--#ARGUMENTS  {} 
--#SEVERITY   CRITICAL 

::= 196867 
 
 -- Current has decreased below lower non-recoverable threshold 
trapUnderCurrentNonRecoverableLow TRAP-TYPE 
ENTERPRISE petevts 
DESCRIPTION  
"Critical Under-Current problem (Lower non-recoverable, going low)" 

--#TYPE       "Current Event" 
--#SUMMARY    "Under-Current Warning (Lower non-recoverable, going low)" 
--#ARGUMENTS  {} 
--#SEVERITY   CRITICAL 

::= 196868 
 
 -- Current has increased above lower non-recoverable threshold 
trapUnderCurrentNonRecoverableHigh TRAP-TYPE 
ENTERPRISE petevts 
DESCRIPTION  
"Critical Under-Current problem (Lower non-recoverable, going high)" 

--#TYPE       "Current Event" 
--#SUMMARY    "Under-Current Warning (Lower non-recoverable, going high)" 
--#ARGUMENTS  {} 
--#SEVERITY   CRITICAL 

::= 196869 
 
-- Current has decreased below Upper non-critical threshold 
trapOverCurrentWarningLow TRAP-TYPE 
ENTERPRISE petevts 
DESCRIPTION  
"Over-Current Warning (Upper non-critical, going low)" 

--#TYPE       "Current Event" 
--#SUMMARY    "Over-Current Warning (Upper non-critical, going low)" 
--#ARGUMENTS  {} 
--#SEVERITY   WARNING 

::= 196870 
 
-- Current has increased above upper non-critical threshold. 
trapOverCurrentWarningHigh TRAP-TYPE 
ENTERPRISE petevts 
DESCRIPTION  
"Over-Current Warning (Upper non-critical, going high)" 

--#TYPE       "Current Event" 
--#SUMMARY    "Over-Current Warning (Upper non-critical, going high)" 
--#ARGUMENTS  {} 
--#SEVERITY   WARNING 

::= 196871 
 
-- Current has decreased below Upper critical threshold 
trapOverCurrentCriticalLow TRAP-TYPE 
ENTERPRISE petevts 
DESCRIPTION  
"Critical Over-Current problem (Upper critical, going low)" 

--#TYPE       "Current Event" 
--#SUMMARY    "Over-Current Warning (Upper critical, going low)" 
--#ARGUMENTS  {} 
--#SEVERITY   CRITICAL 

::= 196872 
 
 -- Current has increased above Upper critical threshold 
trapOverCurrentCriticalHigh TRAP-TYPE 
ENTERPRISE petevts 
DESCRIPTION  
"Critical Over-Current problem (Upper critical, going high)" 

--#TYPE       "Current Event" 
--#SUMMARY    "Over-Current Warning (Upper critical, going high)" 
--#ARGUMENTS  {} 
--#SEVERITY   CRITICAL 

::= 196873 
 
 -- Current has decreased below Upper non-recoverable threshold 
trapOverCurrentNonRecoverableLow TRAP-TYPE 
ENTERPRISE petevts 
DESCRIPTION  
"Critical Over-Current problem (Upper non-recoverable, going low)" 

--#TYPE       "Current Event" 
--#SUMMARY    "Over-Current Warning (Upper non-recoverable, going low)" 
--#ARGUMENTS  {} 
--#SEVERITY   CRITICAL 

::= 196874 
 
 -- Current has increased above Upper non-recoverable threshold 
trapOverCurrentNonRecoverableHigh TRAP-TYPE 
ENTERPRISE petevts 
DESCRIPTION  
"Critical Over-Current problem (Upper non-recoverable, going high)" 

--#TYPE       "Current Event" 
--#SUMMARY    "Under-Current Warning (Upper non-recoverable, going high)" 
--#ARGUMENTS  {} 
--#SEVERITY   CRITICAL 

::= 196875 
 
-- Current decreased below lower non-critical threshold Cleared 
trapUnderCurrentWarningLowCleared TRAP-TYPE 
ENTERPRISE petevts 
DESCRIPTION  
"Under-Current Warning (Lower non-critical, going low) Cleared" 

--#TYPE       "Current Event" 
--#SUMMARY    "Under-Current Warning (Lower non-critical, going low) Cleared" 
--#ARGUMENTS  {} 
--#SEVERITY   INFORMATIONAL 

::= 196992 
 
-- Current increased above lower non-critical threshold Cleared 
trapUnderCurrentWarningHighCleared TRAP-TYPE 
ENTERPRISE petevts 
DESCRIPTION  
"Under-Current Warning (Lower non-critical, going high)Cleared" 

--#TYPE       "Current Event" 
--#SUMMARY    "Under-Current Warning (Lower non-critical, going high)Cleared" 
--#ARGUMENTS  {} 
--#SEVERITY   INFORMATIONAL 

::= 196993 
 
-- Current decreased below lower critical threshold Cleared 
trapUnderCurrentCriticalLowCleared TRAP-TYPE 
ENTERPRISE petevts 
DESCRIPTION  
"Critical Under-Current problem (Lower critical, going low)Cleared" 

--#TYPE       "Current Event" 
--#SUMMARY    "Under-Current Warning (Lower critical, going low)Cleared" 
--#ARGUMENTS  {} 
--#SEVERITY   INFORMATIONAL 

::= 196994 
 
 -- Current increased above lower critical threshold Cleared 
trapUnderCurrentCriticalHighCleared TRAP-TYPE 
ENTERPRISE petevts 
DESCRIPTION  
"Critical Under-Current problem (Lower critical, going high) Cleared" 

--#TYPE       "Current Event" 
--#SUMMARY    "Under-Current Warning (Lower critical, going high) Cleared" 
--#ARGUMENTS  {} 
--#SEVERITY   INFORMATIONAL 

::= 196995 
 
 -- Current decreased below lower non-recoverable threshold Cleared 
trapUnderCurrentNonRecoverableLowCleared TRAP-TYPE 
ENTERPRISE petevts 
DESCRIPTION  
"Critical Under-Current problem (Lower non-recoverable, going low)Cleared" 

--#TYPE       "Current Event" 
--#SUMMARY    "Under-Current Warning (Lower non-recoverable, going low)Cleared" 
--#ARGUMENTS  {} 
--#SEVERITY   INFORMATIONAL 

::= 196996 
 
 -- Current increased above lower non-recoverable threshold Cleared 
trapUnderCurrentNonRecoverableHighCleared TRAP-TYPE 
ENTERPRISE petevts 
DESCRIPTION  
"Critical Under-Current problem (Lower non-recoverable, going high) Cleared" 

--#TYPE       "Current Event" 
--#SUMMARY    "Under-Current Warning (Lower non-recoverable, going high) Cleared" 
--#ARGUMENTS  {} 
--#SEVERITY   INFORMATIONAL 

::= 196997 
 
-- Current decreased below Upper non-critical threshold Cleared 
trapOverCurrentWarningLowCleared TRAP-TYPE 
ENTERPRISE petevts 
DESCRIPTION  
"Over-Current Warning (Upper non-critical, going low) Cleared" 

--#TYPE       "Current Event" 
--#SUMMARY    "Over-Current Warning (Upper non-critical, going low) Cleared" 
--#ARGUMENTS  {} 
--#SEVERITY   INFORMATIONAL 

::= 196998 
 
-- Current increased above upper non-critical threshold Cleared 
trapOverCurrentWarningHighCleared TRAP-TYPE 
ENTERPRISE petevts 
DESCRIPTION  
"Over-Current Warning (Upper non-critical, going high)Cleared" 

--#TYPE       "Current Event" 
--#SUMMARY    "Over-Current Warning (Upper non-critical, going high)Cleared" 
--#ARGUMENTS  {} 
--#SEVERITY   INFORMATIONAL 

::= 196999 
 
-- Current decreased below Upper critical threshold Cleared 
trapOverCurrentCriticalLowCleared TRAP-TYPE 
ENTERPRISE petevts 
DESCRIPTION  
"Critical Over-Current problem (Upper critical, going low) Cleared" 

--#TYPE       "Current Event" 
--#SUMMARY    "Over-Current Warning (Upper critical, going low) Cleared" 
--#ARGUMENTS  {} 
--#SEVERITY   INFORMATIONAL 

::= 197000 
 
 -- Current increased above Upper critical threshold Cleared 
trapOverCurrentCriticalHighCleared TRAP-TYPE 
ENTERPRISE petevts 
DESCRIPTION  
"Critical Over-Current problem (Upper critical, going high)Cleared" 

--#TYPE       "Current Event" 
--#SUMMARY    "Over-Current Warning (Upper critical, going high)Cleared" 
--#ARGUMENTS  {} 
--#SEVERITY   INFORMATIONAL 

::= 197001 
 
 -- Current decreased below Upper non-recoverable threshold Cleared 
trapOverCurrentNonRecoverableLowCleared TRAP-TYPE 
ENTERPRISE petevts 
DESCRIPTION  
"Critical Over-Current problem (Upper non-recoverable, going low)Cleared" 

--#TYPE       "Current Event" 
--#SUMMARY    "Over-Current Warning (Upper non-recoverable, going low)Cleared" 
--#ARGUMENTS  {} 
--#SEVERITY   INFORMATIONAL 

::= 197002 
 
 -- Current increased above Upper non-recoverable threshold Cleared 
trapOverCurrentNonRecoverableHighCleared TRAP-TYPE 
ENTERPRISE petevts 
DESCRIPTION  
"Critical Over-Current problem (Upper non-recoverable, going high) Cleared" 

--#TYPE       "Current Event" 
--#SUMMARY    "Under-Current Warning (Upper non-recoverable, going high) Cleared" 
--#ARGUMENTS  {} 
--#SEVERITY   INFORMATIONAL 

::= 197003 
 
 
-- ********************************************** 
-- *		Fan			* 
-- ********************************************** 

-- Fan speed has decreased below lower non-critical threshold 
trapFanUnderSpeedWarningLow TRAP-TYPE 
ENTERPRISE petevts 
DESCRIPTION  
"Fan Under Speed Warning (Lower non-critical, going low)" 

--#TYPE       "Fan Event" 
--#SUMMARY    "Fan Under Speed Warning (Lower non-critical, going low)" 
--#ARGUMENTS  {} 
--#SEVERITY   WARNING 

::= 262400 
 
-- Fan speed has increased above lower non-critical threshold 
trapFanUnderSpeedWarningHigh TRAP-TYPE 
ENTERPRISE petevts 
DESCRIPTION  
"Fan Under Speed Warning (Lower non-critical, going high)" 

--#TYPE       "Fan Event" 
--#SUMMARY    "Fan Under Speed Warning (Lower non-critical, going high)" 
--#ARGUMENTS  {} 
--#SEVERITY   WARNING 

::= 262401 
 
-- Fan speed has decreased below lower critical threshold 
trapFanUnderSpeedCriticalLow TRAP-TYPE 
ENTERPRISE petevts 
DESCRIPTION  
"Critical Fan Under Speed problem (Lower critical, going low)" 

--#TYPE       "Fan Event" 
--#SUMMARY    "Fan Under Speed Warning (Lower critical, going low)" 
--#ARGUMENTS  {} 
--#SEVERITY   CRITICAL 

::= 262402 
 
 -- Fan speed has increased above lower critical threshold 
trapFanUnderSpeedCriticalHigh TRAP-TYPE 
ENTERPRISE petevts 
DESCRIPTION  
"Critical Fan Under Speed problem (Lower critical, going high)" 

--#TYPE       "Fan Event" 
--#SUMMARY    "Fan Under Speed Warning (Lower critical, going high)" 
--#ARGUMENTS  {} 
--#SEVERITY   CRITICAL 

::= 262403 
 
 -- Fan speed has decreased below lower non-recoverable threshold 
trapFanUnderSpeedNonRecoverableLow TRAP-TYPE 
ENTERPRISE petevts 
DESCRIPTION  
"Critical Fan Under Speed problem (Lower non-recoverable, going low)" 

--#TYPE       "Fan Event" 
--#SUMMARY    "Fan Under Speed Warning (Lower non-recoverable, going low)" 
--#ARGUMENTS  {} 
--#SEVERITY   CRITICAL 

::= 262404 
 
 -- Fan speed has increased above lower non-recoverable threshold 
trapFanUnderSpeedNonRecoverableHigh TRAP-TYPE 
ENTERPRISE petevts 
DESCRIPTION  
"Critical Fan Under Speed problem (Lower non-recoverable, going high)" 

--#TYPE       "Fan Event" 
--#SUMMARY    "Fan Under Speed Warning (Lower non-recoverable, going high)" 
--#ARGUMENTS  {} 
--#SEVERITY   CRITICAL 

::= 262405 
 
-- Fan speed has decreased below Upper non-critical threshold 
trapFanOverSpeedWarningLow TRAP-TYPE 
ENTERPRISE petevts 
DESCRIPTION  
"Fan Over Speed Warning (Upper non-critical, going low)" 

--#TYPE       "Fan Event" 
--#SUMMARY    "Fan Over Speed Warning (Upper non-critical, going low)" 
--#ARGUMENTS  {} 
--#SEVERITY   WARNING 

::= 262406 
 
-- Fan speed has increased above upper non-critical threshold. 
trapFanOverSpeedWarningHigh TRAP-TYPE 
ENTERPRISE petevts 
DESCRIPTION  
"Fan Over Speed Warning (Upper non-critical, going high)" 

--#TYPE       "Fan Event" 
--#SUMMARY    "Fan Over Speed Warning (Upper non-critical, going high)" 
--#ARGUMENTS  {} 
--#SEVERITY   WARNING 

::= 262407 
 
-- Fan speed has decreased below Upper critical threshold 
trapFanOverSpeedCriticalLow TRAP-TYPE 
ENTERPRISE petevts 
DESCRIPTION  
"Critical Fan Over Speed problem (Upper critical, going low)" 

--#TYPE       "Fan Event" 
--#SUMMARY    "Fan Over Speed Warning (Upper critical, going low)" 
--#ARGUMENTS  {} 
--#SEVERITY   CRITICAL 

::= 262408 
 
 -- Fan speed has increased above Upper critical threshold 
trapFanOverSpeedCriticalHigh TRAP-TYPE 
ENTERPRISE petevts 
DESCRIPTION  
"Critical Fan Over Speed problem (Upper critical, going high)" 

--#TYPE       "Fan Event" 
--#SUMMARY    "Fan Over Speed Warning (Upper critical, going high)" 
--#ARGUMENTS  {} 
--#SEVERITY   CRITICAL 

::= 262409 
 
 -- Fan speed has decreased below Upper non-recoverable threshold 
trapFanOverSpeedNonRecoverableLow TRAP-TYPE 
ENTERPRISE petevts 
DESCRIPTION  
"Critical Fan Over Speed problem (Upper non-recoverable, going low)" 

--#TYPE       "Fan Event" 
--#SUMMARY    "Fan Over Speed Warning (Upper non-recoverable, going low)" 
--#ARGUMENTS  {} 
--#SEVERITY   CRITICAL 

::= 262410 
 
 -- Fan speed has increased above Upper non-recoverable threshold 
trapFanOverSpeedNonRecoverableHigh TRAP-TYPE 
ENTERPRISE petevts 
DESCRIPTION  
"Critical Fan Over Speed problem (Upper non-recoverable, going high)" 

--#TYPE       "Fan Event" 
--#SUMMARY    "Fan Under Speed Warning (Upper non-recoverable, going high)" 
--#ARGUMENTS  {} 
--#SEVERITY   CRITICAL 

::= 262411 
 
-- Fan speed has increased above Upper non-recoverable threshold 
trapWxlTest TRAP-TYPE 
ENTERPRISE petevts 
DESCRIPTION  
"test" 

--#TYPE       "Fan Event" 
--#SUMMARY    "Fan Under Speed Warning (Upper non-recoverable, going high)" 
--#ARGUMENTS  {} 
--#SEVERITY   CRITICAL 

::= 262412 
 
-- Fan speed decreased below lower non-critical threshold Cleared 
trapFanUnderSpeedWarningLowCleared TRAP-TYPE 
ENTERPRISE petevts 
DESCRIPTION  
"Fan Under Speed Warning (Lower non-critical, going low) Cleared" 

--#TYPE       "Fan Event" 
--#SUMMARY    "Fan Under Speed Warning (Lower non-critical, going low) Cleared" 
--#ARGUMENTS  {} 
--#SEVERITY   INFORMATIONAL 

::= 262528 
 
-- Fan speed increased above lower non-critical threshold Cleared 
trapFanUnderSpeedWarningHighCleared TRAP-TYPE 
ENTERPRISE petevts 
DESCRIPTION  
"Fan Under Speed Warning (Lower non-critical, going high)Cleared" 

--#TYPE       "Fan Event" 
--#SUMMARY    "Fan Under Speed Warning (Lower non-critical, going high)Cleared" 
--#ARGUMENTS  {} 
--#SEVERITY   INFORMATIONAL 

::= 262529 
 
-- Fan speed decreased below lower critical threshold Cleared 
trapFanUnderSpeedCriticalLowCleared TRAP-TYPE 
ENTERPRISE petevts 
DESCRIPTION  
"Critical Fan Under Speed problem (Lower critical, going low)Cleared" 

--#TYPE       "Fan Event" 
--#SUMMARY    "Fan Under Speed Warning (Lower critical, going low)Cleared" 
--#ARGUMENTS  {} 
--#SEVERITY   INFORMATIONAL 

::= 262530 
 
 -- Fan speed increased above lower critical threshold Cleared 
trapFanUnderSpeedCriticalHighCleared TRAP-TYPE 
ENTERPRISE petevts 
DESCRIPTION  
"Critical Fan Under Speed problem (Lower critical, going high) Cleared" 

--#TYPE       "Fan Event" 
--#SUMMARY    "Fan Under Speed Warning (Lower critical, going high) Cleared" 
--#ARGUMENTS  {} 
--#SEVERITY   INFORMATIONAL 

::= 262531 
 
 -- Fan speed decreased below lower non-recoverable threshold Cleared 
trapFanUnderSpeedNonRecoverableLowCleared TRAP-TYPE 
ENTERPRISE petevts 
DESCRIPTION  
"Critical Fan Under Speed problem (Lower non-recoverable, going low)Cleared" 

--#TYPE       "Fan Event" 
--#SUMMARY    "Fan Under Speed Warning (Lower non-recoverable, going low)Cleared" 
--#ARGUMENTS  {} 
--#SEVERITY   INFORMATIONAL 

::= 262532 
 
 -- Fan speed increased above lower non-recoverable threshold Cleared 
trapFanUnderSpeedNonRecoverableHighCleared TRAP-TYPE 
ENTERPRISE petevts 
DESCRIPTION  
"Critical Fan Under Speed problem (Lower non-recoverable, going high) Cleared" 

--#TYPE       "Fan Event" 
--#SUMMARY    "Fan Under Speed Warning (Lower non-recoverable, going high) Cleared" 
--#ARGUMENTS  {} 
--#SEVERITY   INFORMATIONAL 

::= 262533 
 
-- Fan speed decreased below Upper non-critical threshold Cleared 
trapFanOverSpeedWarningLowCleared TRAP-TYPE 
ENTERPRISE petevts 
DESCRIPTION  
"Fan Over Speed Warning (Upper non-critical, going low) Cleared" 

--#TYPE       "Fan Event" 
--#SUMMARY    "Fan Over Speed Warning (Upper non-critical, going low) Cleared" 
--#ARGUMENTS  {} 
--#SEVERITY   INFORMATIONAL 

::= 262534 
 
-- Fan speed increased above upper non-critical threshold Cleared 
trapFanOverSpeedWarningHighCleared TRAP-TYPE 
ENTERPRISE petevts 
DESCRIPTION  
"Fan Over Speed Warning (Upper non-critical, going high)Cleared" 

--#TYPE       "Fan Event" 
--#SUMMARY    "Fan Over Speed Warning (Upper non-critical, going high)Cleared" 
--#ARGUMENTS  {} 
--#SEVERITY   INFORMATIONAL 

::= 262535 
 
-- Fan speed decreased below Upper critical threshold Cleared 
trapFanOverSpeedCriticalLowCleared TRAP-TYPE 
ENTERPRISE petevts 
DESCRIPTION  
"Critical Fan Over Speed problem (Upper critical, going low) Cleared" 

--#TYPE       "Fan Event" 
--#SUMMARY    "Fan Over Speed Warning (Upper critical, going low) Cleared" 
--#ARGUMENTS  {} 
--#SEVERITY   INFORMATIONAL 

::= 262536 
 
 -- Fan speed increased above Upper critical threshold Cleared 
trapFanOverSpeedCriticalHighCleared TRAP-TYPE 
ENTERPRISE petevts 
DESCRIPTION  
"Critical Fan Over Speed problem (Upper critical, going high)Cleared" 

--#TYPE       "Fan Event" 
--#SUMMARY    "Fan Over Speed Warning (Upper critical, going high)Cleared" 
--#ARGUMENTS  {} 
--#SEVERITY   INFORMATIONAL 

::= 262537 
 
 -- Fan speed decreased below Upper non-recoverable threshold Cleared 
trapFanOverSpeedNonRecoverableLowCleared TRAP-TYPE 
ENTERPRISE petevts 
DESCRIPTION  
"Critical Fan Over Speed problem (Upper non-recoverable, going low)Cleared" 

--#TYPE       "Fan Event" 
--#SUMMARY    "Fan Over Speed Warning (Upper non-recoverable, going low)Cleared" 
--#ARGUMENTS  {} 
--#SEVERITY   INFORMATIONAL 

::= 262538 
 
 -- Fan speed increased above Upper non-recoverable threshold Cleared 
trapFanOverSpeedNonRecoverableHighCleared TRAP-TYPE 
ENTERPRISE petevts 
DESCRIPTION  
"Critical Fan Over Speed problem (Upper non-recoverable, going high) Cleared" 

--#TYPE       "Fan Event" 
--#SUMMARY    "Fan Under Speed Warning (Upper non-recoverable, going high) Cleared" 
--#ARGUMENTS  {} 
--#SEVERITY   INFORMATIONAL 

::= 262539 
 
 -- Fan Removed/Absent 
trapFanRemoved TRAP-TYPE 
ENTERPRISE petevts 
DESCRIPTION  
 "Fan Removed/Absent" 

--#TYPE       "Fan Event" 
--#SUMMARY    "Fan Removed/Absent" 
--#ARGUMENTS  {} 
--#SEVERITY   CRITICAL 

::= 264192 
 
  -- Fan Inserted/Present 
trapFanInserted TRAP-TYPE 
ENTERPRISE petevts 
DESCRIPTION  
 "Fan Inserted/Present" 

--#TYPE       "Fan Event" 
--#SUMMARY    "Fan Inserted/Present" 
--#ARGUMENTS  {} 
--#SEVERITY   INFORMATIONAL 

::= 264193 
 
-- Fan Full Redundancy  
trapFanFullRedundancy TRAP-TYPE 
ENTERPRISE petevts 
DESCRIPTION  
 "Fan redundancy has returned to Normal" 

--#TYPE       "Fan Event" 
--#SUMMARY    "Fan redundancy has returned to Normal" 
--#ARGUMENTS  {} 
--#SEVERITY   INFORMATIONAL 

::= 264960 

-- Fan Redundancy lost  
trapFanRedundancyLost TRAP-TYPE 
ENTERPRISE petevts 
DESCRIPTION  
 "Fan Redundancy has been Lost" 

--#TYPE       "Fan Event" 
--#SUMMARY    "Fan Redundancy has been Lost" 
--#ARGUMENTS  {} 
--#SEVERITY   CRITICAL 

::= 264961 

-- Fan Redundancy degraded 
trapFanRedundancyDegraded TRAP-TYPE 
ENTERPRISE petevts 
DESCRIPTION  
 "Fan Redundancy is in a degraded state" 

--#TYPE       "Fan Event" 
--#SUMMARY    "Fan Redundancy is in a degraded state" 
--#ARGUMENTS  {} 
--#SEVERITY   WARNING 

::= 264962 
 
--********************** 
--* Chassis Intrusion  * 
--********************** 

-- Chassis Intrusion 
trapChassisIntrusion TRAP-TYPE 
ENTERPRISE petevts 
DESCRIPTION  
 "Chassis Intrusion - Physical Security Violation" 

--#TYPE       "Chassis Intrusion Event" 
--#SUMMARY    "Chassis Intrusion - Physical Security Violation" 
--#ARGUMENTS  {} 
--#SEVERITY   CRITICAL 

::= 356096 

-- Chassis Drive Bay Intrusion 
trapChassisDriveBayIntrusion TRAP-TYPE 
ENTERPRISE petevts 
DESCRIPTION  
 "Chassis Intrusion - Drive Bay Violation" 

--#TYPE       "Chassis Intrusion Event" 
--#SUMMARY    "Chassis Intrusion - Drive Bay Violation" 
--#ARGUMENTS  {} 
--#SEVERITY   CRITICAL 

::= 356097 
 
 -- I/O Card Area Intrusion 
trapChassisIOCardAreaIntrusion TRAP-TYPE 
ENTERPRISE petevts 
DESCRIPTION  
 "I/O Card Area Intrusion" 

--#TYPE       "Chassis Intrusion Event" 
--#SUMMARY    "I/O Card Area Intrusion" 
--#ARGUMENTS  {} 
--#SEVERITY   CRITICAL 

::= 356098 
 
  -- Processor Area Intrusion 
trapChassisProcessorAreaIntrusion TRAP-TYPE 
ENTERPRISE petevts 
DESCRIPTION  
 "Processor Area Intrusion" 

--#TYPE       "Chassis Intrusion Event" 
--#SUMMARY    "Processor Area Intrusion" 
--#ARGUMENTS  {} 
--#SEVERITY   CRITICAL 

::= 356099 
 
   -- LAN Leash Lost 
trapChassisLANLeashLost TRAP-TYPE 
ENTERPRISE petevts 
DESCRIPTION  
 "LAN Leash Lost" 

--#TYPE       "Chassis Intrusion Event" 
--#SUMMARY    "LAN Leash Lost" 
--#ARGUMENTS  {} 
--#SEVERITY   CRITICAL 

::= 356100 
 
    -- Unauthorized dock 
trapChassisUnauthorizedDock TRAP-TYPE 
ENTERPRISE petevts 
DESCRIPTION  
 "Unauthorized dock" 

--#TYPE       "Chassis Intrusion Event" 
--#SUMMARY    "Unauthorized dock" 
--#ARGUMENTS  {} 
--#SEVERITY   CRITICAL 

::= 356101 
 
     -- Fan Area Intrusion 
trapChassisFanAreaIntrusion TRAP-TYPE 
ENTERPRISE petevts 
DESCRIPTION  
 "Fan Area Intrusion" 

--#TYPE       "Chassis Intrusion Event" 
--#SUMMARY    "Fan Area Intrusion" 
--#ARGUMENTS  {} 
--#SEVERITY   CRITICAL 

::= 356102 
 
-- Chassis Intrusion cleared 
trapChassisIntrusionCleared TRAP-TYPE 
ENTERPRISE petevts 
DESCRIPTION  
"Chassis Intrusion (Physical Security Violation) Event Cleared" 

--#TYPE       "Chassis Intrusion Event" 
--#SUMMARY    "Chassis Intrusion( Physical Security Violation) Event Cleared" 
--#ARGUMENTS  {} 
--#SEVERITY   INFORMATIONAL 

::= 356224 

 -- Chassis Drive Bay Intrusion Cleared 
trapChassisDriveBayIntrusionCleared TRAP-TYPE 
ENTERPRISE petevts 
DESCRIPTION  
 "Chassis Intrusion - Drive Bay Violation Cleared" 

--#TYPE       "Chassis Intrusion Event" 
--#SUMMARY    "Chassis Intrusion - Drive Bay Violation Cleared" 
--#ARGUMENTS  {} 
--#SEVERITY   INFORMATIONAL 

::= 356225 
 
  -- I/O Card Area Intrusion Cleared 
trapChassisIOCardAreaIntrusionCleared TRAP-TYPE 
ENTERPRISE petevts 
DESCRIPTION  
 "I/O Card Area Intrusion Cleared" 

--#TYPE       "Chassis Intrusion Event" 
--#SUMMARY    "I/O Card Area Intrusion Cleared" 
--#ARGUMENTS  {} 
--#SEVERITY   INFORMATIONAL 

::= 356226 
 
  -- Processor Area Intrusion Cleared 
trapChassisProcessorAreaIntrusionCleared TRAP-TYPE 
ENTERPRISE petevts 
DESCRIPTION  
 "Processor Area Intrusion Cleared" 

--#TYPE       "Chassis Intrusion Event" 
--#SUMMARY    "Processor Area Intrusion Cleared" 
--#ARGUMENTS  {} 
--#SEVERITY   INFORMATIONAL 

::= 356227 
 
   -- LAN Leash Lost Cleared 
trapChassisLANLeashLostCleared TRAP-TYPE 
ENTERPRISE petevts 
DESCRIPTION  
 "LAN Leash Lost" 

--#TYPE       "Chassis Intrusion Event" 
--#SUMMARY    "LAN Leash Lost Cleared" 
--#ARGUMENTS  {} 
--#SEVERITY   INFORMATIONAL 

::= 356228 
 
    -- Unauthorized dock Cleared 
trapChassisUnauthorizedDockCleared TRAP-TYPE 
ENTERPRISE petevts 
DESCRIPTION  
 "Unauthorized dock Cleared" 

--#TYPE       "Chassis Intrusion Event" 
--#SUMMARY    "Unauthorized dock Cleared" 
--#ARGUMENTS  {} 
--#SEVERITY   INFORMATIONAL 

::= 356229 
 
     -- Fan Area Intrusion Cleared 
trapChassisFanAreaIntrusionCleared TRAP-TYPE 
ENTERPRISE petevts 
DESCRIPTION  
 "Fan Area Intrusion Cleared" 

--#TYPE       "Chassis Intrusion Event" 
--#SUMMARY    "Fan Area Intrusion Cleared" 
--#ARGUMENTS  {} 
--#SEVERITY   INFORMATIONAL 

::= 356230 

--********************** 
--* Platform Security  * 
--********************** 
    -- Secure Mode Violation Attempt 
trapSecureModeViolation TRAP-TYPE 
ENTERPRISE petevts 
DESCRIPTION  
 "Secure Mode Violation Attempt" 

--#TYPE       "Platform Securtiy Violation Attempt Event" 
--#SUMMARY    "Secure Mode Violation Attempt" 
--#ARGUMENTS  {} 
--#SEVERITY   CRITICAL 

::= 421632 
 
     -- User Password Violation Attempt 
trapUserPasswordViolation TRAP-TYPE 
ENTERPRISE petevts 
DESCRIPTION  
 "User Password Violation Attempt" 

--#TYPE       "Platform Securtiy Violation Attempt Event" 
--#SUMMARY    "User Password Violation Attempt" 
--#ARGUMENTS  {} 
--#SEVERITY   CRITICAL 

::= 421633 

      -- Setup Password Violation Attempt 
trapSetupPasswordViolation TRAP-TYPE 
ENTERPRISE petevts 
DESCRIPTION  
 "Setup Password Violation Attempt" 

--#TYPE       "Platform Securtiy Violation Attempt Event" 
--#SUMMARY    "Setup Password Violation Attempt" 
--#ARGUMENTS  {} 
--#SEVERITY   CRITICAL 

::= 421634 
 
       -- Network Boot Password Violation Attempt 
trapNetworkBootPasswordViolation TRAP-TYPE 
ENTERPRISE petevts 
DESCRIPTION  
 "Network Boot Password Violation Attempt" 

--#TYPE       "Platform Securtiy Violation Attempt Event" 
--#SUMMARY    "Network boot Password Violation Attempt" 
--#ARGUMENTS  {} 
--#SEVERITY   CRITICAL 

::= 421635 
 
       -- Other Pre-boot Password Violation Attempt 
trapOtherPasswordViolation TRAP-TYPE 
ENTERPRISE petevts 
DESCRIPTION  
 "Other Pre-boot Password Violation Attempt" 

--#TYPE       "Platform Securtiy Violation Attempt Event" 
--#SUMMARY    "Other pre-boot Password Violation Attempt" 
--#ARGUMENTS  {} 
--#SEVERITY   CRITICAL 

::= 421636 
 
       -- Out-of-band access Password Violation Attempt 
trapOutOfBandAccessViolation TRAP-TYPE 
ENTERPRISE petevts 
DESCRIPTION  
 "Out-of-band access Violation Attempt" 

--#TYPE       "Platform Securtiy Violation Attempt Event" 
--#SUMMARY    "Out-of-band access Violation Attempt" 
--#ARGUMENTS  {} 
--#SEVERITY   CRITICAL 

::= 421637 
 
     -- Secure Mode Violation Attempt Cleared 
trapSecureModeViolationCleared TRAP-TYPE 
ENTERPRISE petevts 
DESCRIPTION  
 "Secure Mode Violation Attempt Cleared" 

--#TYPE       "Platform Securtiy Violation Attempt Event" 
--#SUMMARY    "Secure Mode Violation Attempt Cleared" 
--#ARGUMENTS  {} 
--#SEVERITY   INFORMATIONAL 

::= 421760 
 
     -- User Password Violation Attempt Cleared  
trapUserPasswordViolationCleared TRAP-TYPE 
ENTERPRISE petevts 
DESCRIPTION  
 "User Password Violation Attempt Cleared" 

--#TYPE       "Platform Securtiy Violation Attempt Event" 
--#SUMMARY    "User Password Violation Attempt Cleared" 
--#ARGUMENTS  {} 
--#SEVERITY   INFORMATIONAL 

::= 421761 

      -- Setup Password Violation Attempt Cleared 
trapSetupPasswordViolationCleared TRAP-TYPE 
ENTERPRISE petevts 
DESCRIPTION  
 "Setup Password Violation Attempt Cleared" 

--#TYPE       "Platform Securtiy Violation Attempt Event" 
--#SUMMARY    "Setup Password Violation Attempt Cleared"  
--#ARGUMENTS  {} 
--#SEVERITY   INFORMATIONAL 

::= 421762 
 
       -- Network Boot Password Violation Attempt Cleared 
trapNetworkBootPasswordViolationCleared TRAP-TYPE 
ENTERPRISE petevts 
DESCRIPTION  
 "Network Boot Password Violation Attempt Cleared" 

--#TYPE       "Platform Securtiy Violation Attempt Event" 
--#SUMMARY    "Network boot Password Violation Attempt Cleared" 
--#ARGUMENTS  {} 
--#SEVERITY   INFORMATIONAL 

::= 421763 
 
       -- Other Pre-boot Password Violation Attempt Cleared 
trapOtherPasswordViolationCleared TRAP-TYPE 
ENTERPRISE petevts 
DESCRIPTION  
 "Other Pre-boot Password Violation Attempt Cleared" 

--#TYPE       "Platform Securtiy Violation Attempt Event" 
--#SUMMARY    "Other pre-boot Password Violation Attempt Cleared" 
--#ARGUMENTS  {} 
--#SEVERITY   INFORMATIONAL 

::= 421764 
 
       -- Out-of-band access Password Violation Attempt Cleared 
trapOutOfBandAccessViolationCleared TRAP-TYPE 
ENTERPRISE petevts 
DESCRIPTION  
 "Out-of-band access Violation Attempt Cleared" 

--#TYPE       "Platform Securtiy Violation Attempt Event" 
--#SUMMARY    "Out-of-band access Violation Attempt Cleared" 
--#ARGUMENTS  {} 
--#SEVERITY   INFORMATIONAL 

::= 421765 
 
 
--********************** 
--* Processor  * 
--********************** 

-- Processor internal error 
trapProcessorInternalError TRAP-TYPE 
ENTERPRISE petevts 
DESCRIPTION  
 "Processor Internal Error" 

--#TYPE       "Processor Event" 
--#SUMMARY    "Processor Internal Error" 
--#ARGUMENTS  {} 
--#SEVERITY   CRITICAL 

::= 487168 
 
-- Processor Thermal Trip 
trapProcessorThermalTrip TRAP-TYPE 
ENTERPRISE petevts 
DESCRIPTION  
"Processor Thermal Trip (Over Temperature Shutdown)" 

--#TYPE       "Processor Event" 
--#SUMMARY    "Processor Thermal Trip (Over Temperature Shutdown)" 
--#ARGUMENTS  {} 
--#SEVERITY   CRITICAL 

::= 487169 

-- Processor Fault Resilient Booting (FRB) 1 / Built-in self test (BIST) Error 
trapProcessorBistError TRAP-TYPE 
ENTERPRISE petevts 
DESCRIPTION  
 "Processor Fault Resilient Booting (FRB) 1 / BIST (Built In Self Test) Failure" 

--#TYPE       "Processor Event" 
--#SUMMARY    "Processor Fault Resilient Booting (FRB) 1 / Processor BIST (Built In Self Test) Failure" 
--#ARGUMENTS  {} 
--#SEVERITY   CRITICAL 

::= 487170 

-- Processor Fault Resilient Booting (FRB) 2 / Hang in Power On Self Test (POST) 
trapProcessorFRB2Failure TRAP-TYPE 
ENTERPRISE petevts 
DESCRIPTION  
 "Processor Fault Resilient Booting (FRB) 2 / Hang in Power On Self Test (POST) Failure" 

--#TYPE       "Processor Event" 
--#SUMMARY    "Processor Fault Resilient Booting (FRB) 2 / Hang in Power On Self Test (POST) Failure" 
--#ARGUMENTS  {} 
--#SEVERITY   CRITICAL  

::= 487171 

-- Processor Fault Resilient Booting (FRB) 3 / Processor Setup / Initialization Failure 
trapProcessorFRB3Failure TRAP-TYPE 
ENTERPRISE petevts 
DESCRIPTION  
 "Processor Fault Resilient Booting (FRB) 3 / Processor Setup / Initialization Failure" 

--#TYPE	"Processor Event" 
--#SUMMARY    "Processor Fault Resilient Booting (FRB) 3 / Processor Setup / Initialization Failure" 
--#ARGUMENTS  {} 
--#SEVERITY   CRITICAL 

::= 487172 

-- Processor config error 
trapProcessorConfigError TRAP-TYPE 
ENTERPRISE petevts 
DESCRIPTION  
 "Processor Configuration Error" 

--#TYPE       "Processor Event" 
--#SUMMARY    "Processor Configuration Error" 
--#ARGUMENTS  {} 
--#SEVERITY   CRITICAL 

::= 487173 
 
-- SM BIOS Uncorrectable CPU-complex Error 
trapSMPIOSUncorrectableCPUComplexError TRAP-TYPE 
ENTERPRISE petevts 
DESCRIPTION  
 "SM BIOS Uncorrectable CPU-complex Error" 

--#TYPE       "Processor Event" 
--#SUMMARY    "SM BIOS Uncorrectable CPU-complex Error" 
--#ARGUMENTS  {} 
--#SEVERITY   CRITICAL 

::= 487174 
 
 -- Processor Presence Detected 
trapProcessorPresenceDetected TRAP-TYPE 
ENTERPRISE petevts 
DESCRIPTION  
 "Processor Presence Detected" 

--#TYPE       "Processor Event" 
--#SUMMARY    "Processor Presence Detected" 
--#ARGUMENTS  {} 
--#SEVERITY   INFORMATIONAL 

::= 487175 
 
  -- Processor Disabled 
trapProcessorDisabled TRAP-TYPE 
ENTERPRISE petevts 
DESCRIPTION  
 "Processor Disabled" 

--#TYPE       "Processor Event" 
--#SUMMARY    "Processor Disabled" 
--#ARGUMENTS  {} 
--#SEVERITY   INFORMATIONAL 

::= 487176 
 
  -- Terminator Presence Detected 
trapTerminatorresenceDetected TRAP-TYPE 
ENTERPRISE petevts 
DESCRIPTION  
 "Terminator Presence Detected" 

--#TYPE       "Processor Event" 
--#SUMMARY    "Terminator Presence Detected" 
--#ARGUMENTS  {} 
--#SEVERITY   INFORMATIONAL 

::= 487177 
 
-- Processor throttle. 
trapProcessorThrottle TRAP-TYPE 
ENTERPRISE petevts 
DESCRIPTION  
 "Processor Throttled (Processor Speed Reduced)" 

--#TYPE       "Processor Event" 
--#SUMMARY    "Processor Throttled (Processor Speed Reduced)" 
--#ARGUMENTS  {} 
--#SEVERITY   WARNING 

::= 487178 
 
-- Processor internal error cleared 
trapProcessorInternalErrorCleared TRAP-TYPE 
ENTERPRISE petevts 
DESCRIPTION  
 "Processor Internal Error Cleared" 

--#TYPE       "Processor Event" 
--#SUMMARY    "Processor Internal Error Cleared" 
--#ARGUMENTS  {} 
--#SEVERITY   INFORMATIONAL 

::= 487296 

-- Processor Back to normal from Thermal Trip 
trapProcessorThermalTripCleared TRAP-TYPE 
ENTERPRISE petevts 
DESCRIPTION  
 "Processor Thermal Trip (Over Temperature Shutdown) Cleared" 

--#TYPE       "Processor Event" 
--#SUMMARY    "Processor Thermal Trip (Over Temperature Shutdown) Cleared" 
--#ARGUMENTS  {} 
--#SEVERITY   INFORMATIONAL 

::= 487297 
 
-- Processor BIST Error cleared 
trapProcessorBistErrorCleared TRAP-TYPE 
ENTERPRISE petevts 
DESCRIPTION  
 "Processor BIST (Built In Self Test) Failure Cleared" 

--#TYPE       "Processor Event" 
--#SUMMARY    "Processor BIST (Built In Self Test) Failure Cleared" 
--#ARGUMENTS  {} 
--#SEVERITY   INFORMATIONAL 

::= 487298 

-- Processor Fault Resilient Booting (FRB) 2 / Hang in Power On Self Test (POST) Cleared 
trapProcessorFRB2FailureCleared TRAP-TYPE 
ENTERPRISE petevts 
DESCRIPTION  
 "Processor Fault Resilient Booting (FRB) 2 / Hang in Power On Self Test (POST) Failure Cleared" 

--#TYPE       "Processor Event" 
--#SUMMARY    "Processor Fault Resilient Booting (FRB) 2 / Hang in Power On Self Test (POST) Failure Cleared" 
--#ARGUMENTS  {} 
--#SEVERITY   INFORMATIONAL  

::= 487299 
 
-- Processor Fault Resilient Booting (FRB) 3 / Processor Setup / Initialization Failure Cleared 
trapProcessorFRB3FailureCleared TRAP-TYPE 
ENTERPRISE petevts 
DESCRIPTION  
 "Processor Fault Resilient Booting (FRB) 3 / Processor Setup / Initialization Failure Cleared" 

--#TYPE	"Processor Event" 
--#SUMMARY    "Processor Fault Resilient Booting (FRB) 3 / Processor Setup / Initialization Failure Cleared" 
--#ARGUMENTS  {} 
--#SEVERITY   INFORMATIONAL 

::= 487300 
 
-- Processor config error cleared 
trapProcessorConfigErrorCleared TRAP-TYPE 
ENTERPRISE petevts 
DESCRIPTION  
 "Processor Configuration Error Cleared" 

--#TYPE       "Processor Event" 
--#SUMMARY    "Processor Configuration Error Cleared" 
--#ARGUMENTS  {} 
--#SEVERITY   INFORMATIONAL 

::= 487301 
 
-- SM BIOS Uncorrectable CPU-complex Error Cleared 
trapSMPIOSUncorrectableCPUComplexErrorCleared TRAP-TYPE 
ENTERPRISE petevts 
DESCRIPTION  
 "SM BIOS Uncorrectable CPU-complex Error Cleared" 

--#TYPE       "Processor Event" 
--#SUMMARY    "SM BIOS Uncorrectable CPU-complex Error Cleared" 
--#ARGUMENTS  {} 
--#SEVERITY   CRITICAL 

::= 487302 
 
-- Processor return to normal from throttled 
trapProcessorThrottleCleared TRAP-TYPE 
ENTERPRISE petevts 
DESCRIPTION  
 "Processor Throttle Cleared (Normal Processor Speed)" 

--#TYPE       "Processor Event" 
--#SUMMARY    "Processor Throttle Cleared (Normal Processor Speed)" 
--#ARGUMENTS  {} 
--#SEVERITY   INFORMATIONAL 

::= 487306 
  
-- Correctable Machine Check Error Cleared 
trapCorrectableMachineCheckErrorCleared TRAP-TYPE 
ENTERPRISE petevts 
DESCRIPTION  
 "Correctable Machine Check Error Cleared" 

--#TYPE       "Processor Event" 
--#SUMMARY    "Correctable Machine Check Error Cleared" 
--#ARGUMENTS  {} 
--#SEVERITY   INFORMATIONAL 

::= 487308 
 
-- ********************************************** 
-- *	Power Supply 				* 
-- ********************************************** 

-- Power Supply State Deasserted 
trapPowerSupplyStateDeasserted TRAP-TYPE 
ENTERPRISE petevts 
DESCRIPTION  
 "Power Supply is disconnected from AC Power." 

--#TYPE       "Power Supply Event" 
--#SUMMARY    "Power Supply is disconnected from AC Power." 
--#ARGUMENTS  {} 
--#SEVERITY   CRITICAL 

::= 525056 

-- Power Supply State Asserted 
trapPowerSupplyStateAsserted TRAP-TYPE 
ENTERPRISE petevts 
DESCRIPTION  
 "Power Supply is connected to AC Power." 

--#TYPE       "Power Supply Event" 
--#SUMMARY    "Power Supply is connected to AC Power." 
--#ARGUMENTS  {} 
--#SEVERITY   INFORMATIONAL 

::= 525057 

-- Predictive Failure Deasserted 
trapPowerSupplyPredictiveFailureAsserted TRAP-TYPE 
ENTERPRISE petevts 
DESCRIPTION  
 "Power Supply Predictive Failure Deasserted" 

--#TYPE       "Power Supply Event" 
--#SUMMARY    "Power Supply Predictive Failure Deasserted" 
--#ARGUMENTS  {} 
--#SEVERITY   CRITICAL 

::= 525313 

-- Predictive Failure Asserted 
trapPowerSupplyPredictiveFailureDeasserted TRAP-TYPE 
ENTERPRISE petevts 
DESCRIPTION  
 "Power Supply Predictive Failure Asserted" 

--#TYPE       "Power Supply Event" 
--#SUMMARY    "Power Supply Predictive Failure Asserted" 
--#ARGUMENTS  {} 
--#SEVERITY   INFORMATIONAL 

::= 525312 
 
-- Power Supply Full Redundancy  
trapPowerSupplyFullRedundancy TRAP-TYPE 
ENTERPRISE petevts 
DESCRIPTION  
 "Power Supply Redundancy Has Returned to Normal" 

--#TYPE       "Power Supply Event" 
--#SUMMARY    "Power Supply Redundancy Has Returned to Normal" 
--#ARGUMENTS  {} 
--#SEVERITY   INFORMATIONAL 

::= 527104 

-- Power Supply Redundancy lost  
trapPowerSupplyRedundancyLost TRAP-TYPE 
ENTERPRISE petevts 
DESCRIPTION  
 "Power Supply Redundancy has been Lost" 

--#TYPE       "Power Supply Event" 
--#SUMMARY    "Power Supply Redundancy has been Lost" 
--#ARGUMENTS  {} 
--#SEVERITY   CRITICAL 

::= 527105 

-- Power Supply Redundancy degraded 
trapPowerSupplyRedundancyDegraded TRAP-TYPE 
ENTERPRISE petevts 
DESCRIPTION  
 "Power Supply Redundancy is in a degraded state" 

--#TYPE       "Power Supply Event" 
--#SUMMARY    "Power Supply Redundancy is in a degraded state" 
--#ARGUMENTS  {} 
--#SEVERITY   WARNING 

::= 527106 

-- Power Supply presence detected 
trapPowerSupplyPresenceDeteced TRAP-TYPE 
ENTERPRISE petevts 
DESCRIPTION  
 "Power Supply Inserted" 

--#TYPE       "Power Supply Event" 
--#SUMMARY    "Power Supply Inserted" 
--#ARGUMENTS  {} 
--#SEVERITY   INFORMATIONAL 

::= 552704 

trapPowerSupplyFailureDetected TRAP-TYPE 
ENTERPRISE petevts 
DESCRIPTION  
 "Power supply Failure detected" 

--#TYPE       "Power Supply Event" 
--#SUMMARY    "Power Supply failure detected" 
--#ARGUMENTS  {} 
--#SEVERITY   CRITICAL 

::= 552705 

trapPowerSupplyWarning TRAP-TYPE 
ENTERPRISE petevts 
DESCRIPTION  
 "Power supply Warning" 

--#TYPE       "Power Supply Event" 
--#SUMMARY    "Power Supply Warning" 
--#ARGUMENTS  {} 
--#SEVERITY   WARNING 

::= 552706 

-- AC Lost 
trapPowerSupplyACLost TRAP-TYPE 
ENTERPRISE petevts 
DESCRIPTION  
 "Power Supply AC Lost" 

--#TYPE       "Power Supply Event" 
--#SUMMARY    "Power Supply AC Lost" 
--#ARGUMENTS  {} 
--#SEVERITY   CRITICAL 

::= 552707 

 -- Power Supply input lost or out-of-range 
trapPowerSupplyInputLost TRAP-TYPE 
ENTERPRISE petevts 
DESCRIPTION  
 "Power Supply input lost or out-of-range" 

--#TYPE       "Power Supply Event" 
--#SUMMARY    "Power Supply input lost or out-of-range" 
--#ARGUMENTS  {} 
--#SEVERITY   CRITICAL 

::= 552708 
 
  -- Power Supply input out-of-range, but present 
trapPowerSupplyInputOutOfRange TRAP-TYPE 
ENTERPRISE petevts 
DESCRIPTION  
 "Power Supply input out-of-range, but present" 

--#TYPE       "Power Supply Event" 
--#SUMMARY    "Power Supply input out-of-range, but present" 
--#ARGUMENTS  {} 
--#SEVERITY   CRITICAL 

::= 552709 
 
  -- Configuration error 
trapPowerSupplyConfigError TRAP-TYPE 
ENTERPRISE petevts 
DESCRIPTION  
 "Power Supply Configuration error" 

--#TYPE       "Power Supply Event" 
--#SUMMARY    "Power Supply Configuration error" 
--#ARGUMENTS  {} 
--#SEVERITY   CRITICAL 

::= 552710 
 
-- Power Supply removed 
trapPowerSupplyPresenceRemoved TRAP-TYPE 
ENTERPRISE petevts 
DESCRIPTION  
"Power Supply Removed" 

--#TYPE       "Power Supply Event" 
--#SUMMARY    "Power Supply Removed" 
--#ARGUMENTS  {} 
--#SEVERITY   WARNING 

::= 552832 

-- Back to normal from failure 
trapPowerSupplyFailureCleared TRAP-TYPE 
ENTERPRISE petevts 
DESCRIPTION  
 "Power Supply Failure Cleared" 

--#TYPE       "Power Supply Event" 
--#SUMMARY    "Power Supply Failure Cleared" 
--#ARGUMENTS  {} 
--#SEVERITY   INFORMATIONAL 

::= 552833 

-- Predictive Failure cleared  
trapPowerSupplyWarningCleared TRAP-TYPE 
ENTERPRISE petevts 
DESCRIPTION  
 "Power Supply Warning Cleared" 

--#TYPE       "Power Supply Event" 
--#SUMMARY    "Power Supply Warning Cleared" 
--#ARGUMENTS  {} 
--#SEVERITY   INFORMATIONAL 

::= 552834 

-- AC Back 
trapPowerSupplyACBack TRAP-TYPE 
ENTERPRISE petevts 
DESCRIPTION  
 "Power Supply AC Restored" 

--#TYPE       "Power Supply Event" 
--#SUMMARY    "Power Supply AC Restored" 
--#ARGUMENTS  {} 
--#SEVERITY   INFORMATIONAL 

::= 552835 

 -- Power Supply input lost or out-of-range Restored 
trapPowerSupplyInputBack TRAP-TYPE 
ENTERPRISE petevts 
DESCRIPTION  
 "Power Supply input lost or out-of-range Restored" 

--#TYPE       "Power Supply Event" 
--#SUMMARY    "Power Supply input lost or out-of-range Restored" 
--#ARGUMENTS  {} 
--#SEVERITY   INFORMATIONAL 

::= 552836 
 
  -- Power Supply input out-of-range is restored 
trapPowerSupplyInputOutOfRangeRestored TRAP-TYPE 
ENTERPRISE petevts 
DESCRIPTION  
 "Power Supply input out-of-range restored"  

--#TYPE       "Power Supply Event" 
--#SUMMARY    "Power Supply input out-of-range restored" 
--#ARGUMENTS  {} 
--#SEVERITY   INFORMATIONAL 

::= 552837 
 
  -- Configuration error Cleared 
trapPowerSupplyConfigErrorCleared TRAP-TYPE 
ENTERPRISE petevts 
DESCRIPTION  
 "Power Supply Configuration error Cleared" 

--#TYPE       "Power Supply Event" 
--#SUMMARY    "Power Supply Configuration error Cleared" 
--#ARGUMENTS  {} 
--#SEVERITY   CRITICAL 

::= 552838 
 

-- ********************************************** 
-- *	Power Unit 				* 
-- ********************************************** 

-- Power Good Sensor events Deasserted 
trapPowerUnitStateDeasserted TRAP-TYPE 
ENTERPRISE petevts 
DESCRIPTION 
 "Run-time power fault has occurred. This state indicates 
  that one or more DC-DC converter have failed or are not operating 
  within nominal specifications." 

--#TYPE         "Power Unit Event" 
--#SUMMARY      "Run-time power fault has occurred." 
--#ARGUMENTS    {} 
--#SEVERITY     CRITICAL 

::= 590592 

-- Power Good Sensor events Asserted 
trapPowerUnitStateAsserted TRAP-TYPE 
ENTERPRISE petevts 
DESCRIPTION 
 "Host power-on sequence has been completed successfully" 

--#TYPE         "Power Unit Event" 
--#SUMMARY      "Host power-on sequence has been completed successfully." 
--#ARGUMENTS    {} 
--#SEVERITY     INFORMATIONAL 

::= 590593 

-- Power Unit Redundancy OK  
trapPowerUnitRedundancyOk TRAP-TYPE 
ENTERPRISE petevts 
DESCRIPTION  
 "Power Unit Redundancy has been restored" 

--#TYPE       "Power Unit Event" 
--#SUMMARY    "Power Unit Redundancy has been restored" 
--#ARGUMENTS  {} 
--#SEVERITY   INFORMATIONAL 

::= 592640 

-- Power Unit Redundancy lost  
trapPowerUnitRedundancyLost TRAP-TYPE 
ENTERPRISE petevts 
DESCRIPTION  
 "Power Unit Redundancy has been Lost" 

--#TYPE       "Power Unit Event" 
--#SUMMARY    "Power Unit Redundancy has been Lost" 
--#ARGUMENTS  {} 
--#SEVERITY   CRITICAL 

::= 592641 

-- Power Off 
trapPowerUnitPowerOff TRAP-TYPE 
ENTERPRISE petevts 
DESCRIPTION 
 "Power unit is off." 

--#TYPE       "Power unit event" 
--#SUMMARY    "Power unit is off." 
--#ARGUMENTS  {} 
--#SEVERITY   INFORMATIONAL 

::= 618240 
 
-- Power Cycle 
trapPowerUnitPowerCycle TRAP-TYPE 
ENTERPRISE petevts 
DESCRIPTION 
 "Power unit is power cycled" 

--#TYPE       "Power unit event" 
--#SUMMARY    "Power unit is power cycled" 
--#ARGUMENTS  {} 
--#SEVERITY   INFORMATIONAL 

::= 618241 
 
-- 240VA Power Down 
trapPowerUnit240VAPowerDown TRAP-TYPE 
ENTERPRISE petevts 
DESCRIPTION 
 "Power unit 240VA Power Down" 

--#TYPE       "Power unit event" 
--#SUMMARY    "Power unit 240VA Power Down" 
--#ARGUMENTS  {} 
--#SEVERITY   INFORMATIONAL 
 
::= 618242 
 
 -- Interlock Power Down 
trapPowerUnitInterlockPowerDown TRAP-TYPE 
ENTERPRISE petevts 
DESCRIPTION 
 "Power unit Interlock Power Down" 

--#TYPE       "Power unit event" 
--#SUMMARY    "Power unit Interlock Power Down" 
--#ARGUMENTS  {} 
--#SEVERITY   INFORMATIONAL 
 
::= 618243 
 
  -- AC lost / Power input lost 
trapPowerUnitACLost TRAP-TYPE 
ENTERPRISE petevts 
DESCRIPTION 
 "Power unit AC lost / Power input lost" 

--#TYPE       "Power unit event" 
--#SUMMARY    "Power unit AC lost / Power input lost" 
--#ARGUMENTS  {} 
--#SEVERITY   INFORMATIONAL 
 
::= 618244 
 
   -- Soft Power Control Failure 
trapPowerUnitSoftPowerControlFail TRAP-TYPE 
ENTERPRISE petevts 
DESCRIPTION 
 "Soft Power Control Failure" 

--#TYPE       "Power unit event" 
--#SUMMARY    "Soft Power Control Failure" 
--#ARGUMENTS  {} 
--#SEVERITY   INFORMATIONAL 
 
::= 618245 
 
-- Power Unit Failure detected 
trapPowerUnitFailure TRAP-TYPE 
ENTERPRISE petevts 
DESCRIPTION 
 "Power Unit Failure detected" 

--#TYPE       "Power unit event" 
--#SUMMARY    "Power Unit Failure detected" 
--#ARGUMENTS  {} 
--#SEVERITY   INFORMATIONAL 
 
::= 618246 
 
-- Predictive Failure 
trapPowerUnitPredictiveFailure TRAP-TYPE 
ENTERPRISE petevts 
DESCRIPTION 
 "Power Unit Predictive Failure" 

--#TYPE       "Power unit event" 
--#SUMMARY    "Power Unit Predictive Failure" 
--#ARGUMENTS  {} 
--#SEVERITY   INFORMATIONAL 
 
::= 618247 
 
-- Power Unit On 
trapPowerUnitPowerOn TRAP-TYPE 
ENTERPRISE petevts 
DESCRIPTION 
 "Power Unit is on." 

--#TYPE       "Power Unit event" 
--#SUMMARY    "Power Unit is on." 
--#ARGUMENTS  {} 
--#SEVERITY   INFORMATIONAL 

::= 618368 
 
-- Power Cycle Completed 
 
trapPowerUnitPowerCycleCompleted TRAP-TYPE 
ENTERPRISE petevts 
DESCRIPTION 
 "Power unit - Power Cycle Completed" 

--#TYPE       "Power unit event" 
--#SUMMARY    "Power unit - Power Cycle Completed" 
--#ARGUMENTS  {} 
--#SEVERITY   INFORMATIONAL 

::= 618369 
 
-- 240VA Power Down 
trapPowerUnit240VAPowerUp TRAP-TYPE 
ENTERPRISE petevts 
DESCRIPTION 
 "Power unit 240VA Power Up" 

--#TYPE       "Power unit event" 
--#SUMMARY    "Power unit 240VA Power Up" 
--#ARGUMENTS  {} 
--#SEVERITY   INFORMATIONAL 
 
::= 618370 
 
 -- Interlock Power Up 
trapPowerUnitInterlockPowerUp TRAP-TYPE 
ENTERPRISE petevts 
DESCRIPTION 
 "Power unit Interlock Power Up" 

--#TYPE       "Power unit event" 
--#SUMMARY    "Power unit Interlock Power Up" 
--#ARGUMENTS  {} 
--#SEVERITY   INFORMATIONAL 
 
::= 618371 
 
  -- AC/Power input restored 
trapPowerUnitACRestored TRAP-TYPE 
ENTERPRISE petevts 
DESCRIPTION 
 "Power unit AC/Power input restored" 

--#TYPE       "Power unit event" 
--#SUMMARY    "Power unit AC/Power input restored" 
--#ARGUMENTS  {} 
--#SEVERITY   INFORMATIONAL 
 
::= 618372 
 
   -- Soft Power Control Failure Cleared 
trapPowerUnitSoftPowerControlFailCleared TRAP-TYPE 
ENTERPRISE petevts 
DESCRIPTION 
 "Soft Power Control Failure Cleared" 

--#TYPE       "Power unit event" 
--#SUMMARY    "Soft Power Control Failure Cleared" 
--#ARGUMENTS  {} 
--#SEVERITY   INFORMATIONAL 
 
::= 618373 
 
-- Power Unit Failure Cleared 
trapPowerUnitFailureCleared TRAP-TYPE 
ENTERPRISE petevts 
DESCRIPTION 
 "Power Unit Failure Cleared" 

--#TYPE       "Power unit event" 
--#SUMMARY    "Power Unit Failure Cleared" 
--#ARGUMENTS  {} 
--#SEVERITY   INFORMATIONAL 
 
::= 618374 
 
-- Predictive Failure Cleared 
trapPowerUnitPredictiveFailureCleared TRAP-TYPE 
ENTERPRISE petevts 
DESCRIPTION 
 "Power Unit Predictive Failure Cleared" 

--#TYPE       "Power unit event" 
--#SUMMARY    "Power Unit Predictive Failure Cleared" 
--#ARGUMENTS  {} 
--#SEVERITY   INFORMATIONAL 
 
::= 618375 

-- ********************************************** 
-- *		Cooling Device 			* 
-- ********************************************** 

-- Cooling Device speed has decreased below lower non-critical threshold 
trapCoolingDeviceUnderSpeedWarningLow TRAP-TYPE 
ENTERPRISE petevts 
DESCRIPTION  
"Cooling Device Under Speed Warning (Lower non-critical, going low)" 

--#TYPE       "Cooling Device Event" 
--#SUMMARY    "Cooling Device Under Speed Warning (Lower non-critical, going low)" 
--#ARGUMENTS  {} 
--#SEVERITY   WARNING 

::= 655616 
 
-- Cooling Device speed has increased above lower non-critical threshold 
trapCoolingDeviceUnderSpeedWarningHigh TRAP-TYPE 
ENTERPRISE petevts 
DESCRIPTION  
"Cooling Device Under Speed Warning (Lower non-critical, going high)" 

--#TYPE       "Cooling Device Event" 
--#SUMMARY    "Cooling Device Under Speed Warning (Lower non-critical, going high)" 
--#ARGUMENTS  {} 
--#SEVERITY   WARNING 

::= 655617 
 
-- Cooling Device speed has decreased below lower critical threshold 
trapCoolingDeviceUnderSpeedCriticalLow TRAP-TYPE 
ENTERPRISE petevts 
DESCRIPTION  
"Critical Cooling Device Under Speed problem (Lower critical, going low)" 

--#TYPE       "Cooling Device Event" 
--#SUMMARY    "Cooling Device Under Speed Warning (Lower critical, going low)" 
--#ARGUMENTS  {} 
--#SEVERITY   CRITICAL 

::= 655618 
 
 -- Cooling Device speed has increased above lower critical threshold 
trapCoolingDeviceUnderSpeedCriticalHigh TRAP-TYPE 
ENTERPRISE petevts 
DESCRIPTION  
"Critical Cooling Device Under Speed problem (Lower critical, going high)" 

--#TYPE       "Cooling Device Event" 
--#SUMMARY    "Cooling Device Under Speed Warning (Lower critical, going high)" 
--#ARGUMENTS  {} 
--#SEVERITY   CRITICAL 

::= 655619 
 
 -- Cooling Device speed has decreased below lower non-recoverable threshold 
trapCoolingDeviceUnderSpeedNonRecoverableLow TRAP-TYPE 
ENTERPRISE petevts 
DESCRIPTION  
"Critical Cooling Device Under Speed problem (Lower non-recoverable, going low)" 

--#TYPE       "Cooling Device Event" 
--#SUMMARY    "Cooling Device Under Speed Warning (Lower non-recoverable, going low)" 
--#ARGUMENTS  {} 
--#SEVERITY   CRITICAL 

::= 655620 
 
 -- Cooling Device speed has increased above lower non-recoverable threshold 
trapCoolingDeviceUnderSpeedNonRecoverableHigh TRAP-TYPE 
ENTERPRISE petevts 
DESCRIPTION  
"Critical Cooling Device Under Speed problem (Lower non-recoverable, going high)" 

--#TYPE       "Cooling Device Event" 
--#SUMMARY    "Cooling Device Under Speed Warning (Lower non-recoverable, going high)" 
--#ARGUMENTS  {} 
--#SEVERITY   CRITICAL 

::= 655621 
 
-- Cooling Device speed has decreased below Upper non-critical threshold 
trapCoolingDeviceOverSpeedWarningLow TRAP-TYPE 
ENTERPRISE petevts 
DESCRIPTION  
"Cooling Device Over Speed Warning (Upper non-critical, going low)" 

--#TYPE       "Cooling Device Event" 
--#SUMMARY    "Cooling Device Over Speed Warning (Upper non-critical, going low)" 
--#ARGUMENTS  {} 
--#SEVERITY   WARNING 

::= 655622 
 
-- Cooling Device speed has increased above upper non-critical threshold. 
trapCoolingDeviceOverSpeedWarningHigh TRAP-TYPE 
ENTERPRISE petevts 
DESCRIPTION  
"Cooling Device Over Speed Warning (Upper non-critical, going high)" 

--#TYPE       "Cooling Device Event" 
--#SUMMARY    "Cooling Device Over Speed Warning (Upper non-critical, going high)" 
--#ARGUMENTS  {} 
--#SEVERITY   WARNING 

::= 655623 
 
-- Cooling Device speed has decreased below Upper critical threshold 
trapCoolingDeviceOverSpeedCriticalLow TRAP-TYPE 
ENTERPRISE petevts 
DESCRIPTION  
"Critical Cooling Device Over Speed problem (Upper critical, going low)" 

--#TYPE       "Cooling Device Event" 
--#SUMMARY    "Cooling Device Over Speed Warning (Upper critical, going low)" 
--#ARGUMENTS  {} 
--#SEVERITY   CRITICAL 

::= 655624 
 
 -- Cooling Device speed has increased above Upper critical threshold 
trapCoolingDeviceOverSpeedCriticalHigh TRAP-TYPE 
ENTERPRISE petevts 
DESCRIPTION  
"Critical Cooling Device Over Speed problem (Upper critical, going high)" 

--#TYPE       "Cooling Device Event" 
--#SUMMARY    "Cooling Device Over Speed Warning (Upper critical, going high)" 
--#ARGUMENTS  {} 
--#SEVERITY   CRITICAL 

::= 655625 
 
 -- Cooling Device speed has decreased below Upper non-recoverable threshold 
trapCoolingDeviceOverSpeedNonRecoverableLow TRAP-TYPE 
ENTERPRISE petevts 
DESCRIPTION  
"Critical Cooling Device Over Speed problem (Upper non-recoverable, going low)" 

--#TYPE       "Cooling Device Event" 
--#SUMMARY    "Cooling Device Over Speed Warning (Upper non-recoverable, going low)" 
--#ARGUMENTS  {} 
--#SEVERITY   CRITICAL 

::= 655626 
 
 -- Cooling Device speed has increased above Upper non-recoverable threshold 
trapCoolingDeviceOverSpeedNonRecoverableHigh TRAP-TYPE 
ENTERPRISE petevts 
DESCRIPTION  
"Critical Cooling Device Over Speed problem (Upper non-recoverable, going high)" 

--#TYPE       "Cooling Device Event" 
--#SUMMARY    "Cooling Device Under Speed Warning (Upper non-recoverable, going high)" 
--#ARGUMENTS  {} 
--#SEVERITY   CRITICAL 

::= 655627 
 
-- Cooling Device speed decreased below lower non-critical threshold Cleared 
trapCoolingDeviceUnderSpeedWarningLowCleared TRAP-TYPE 
ENTERPRISE petevts 
DESCRIPTION  
"Cooling Device Under Speed Warning (Lower non-critical, going low) Cleared" 

--#TYPE       "Cooling Device Event" 
--#SUMMARY    "Cooling Device Under Speed Warning (Lower non-critical, going low) Cleared" 
--#ARGUMENTS  {} 
--#SEVERITY   INFORMATIONAL 

::= 655744 
 
-- Cooling Device speed increased above lower non-critical threshold Cleared 
trapCoolingDeviceUnderSpeedWarningHighCleared TRAP-TYPE 
ENTERPRISE petevts 
DESCRIPTION  
"Cooling Device Under Speed Warning (Lower non-critical, going high)Cleared" 

--#TYPE       "Cooling Device Event" 
--#SUMMARY    "Cooling Device Under Speed Warning (Lower non-critical, going high)Cleared" 
--#ARGUMENTS  {} 
--#SEVERITY   INFORMATIONAL 

::= 655745 
 
-- Cooling Device speed decreased below lower critical threshold Cleared 
trapCoolingDeviceUnderSpeedCriticalLowCleared TRAP-TYPE 
ENTERPRISE petevts 
DESCRIPTION  
"Critical Cooling Device Under Speed problem (Lower critical, going low)Cleared" 

--#TYPE       "Cooling Device Event" 
--#SUMMARY    "Cooling Device Under Speed Warning (Lower critical, going low)Cleared" 
--#ARGUMENTS  {} 
--#SEVERITY   INFORMATIONAL 

::= 655746 
 
 -- Cooling Device speed increased above lower critical threshold Cleared 
trapCoolingDeviceUnderSpeedCriticalHighCleared TRAP-TYPE 
ENTERPRISE petevts 
DESCRIPTION  
"Critical Cooling Device Under Speed problem (Lower critical, going high) Cleared" 

--#TYPE       "Cooling Device Event" 
--#SUMMARY    "Cooling Device Under Speed Warning (Lower critical, going high) Cleared" 
--#ARGUMENTS  {} 
--#SEVERITY   INFORMATIONAL 

::= 655747 
 
 -- Cooling Device speed decreased below lower non-recoverable threshold Cleared 
trapCoolingDeviceUnderSpeedNonRecoverableLowCleared TRAP-TYPE 
ENTERPRISE petevts 
DESCRIPTION  
"Critical Cooling Device Under Speed problem (Lower non-recoverable, going low)Cleared" 

--#TYPE       "Cooling Device Event" 
--#SUMMARY    "Cooling Device Under Speed Warning (Lower non-recoverable, going low)Cleared" 
--#ARGUMENTS  {} 
--#SEVERITY   INFORMATIONAL 

::= 655748 
 
 -- Cooling Device speed increased above lower non-recoverable threshold Cleared 
trapCoolingDeviceUnderSpeedNonRecoverableHighCleared TRAP-TYPE 
ENTERPRISE petevts 
DESCRIPTION  
"Critical Cooling Device Under Speed problem (Lower non-recoverable, going high) Cleared" 

--#TYPE       "Cooling Device Event" 
--#SUMMARY    "Cooling Device Under Speed Warning (Lower non-recoverable, going high) Cleared" 
--#ARGUMENTS  {} 
--#SEVERITY   INFORMATIONAL 

::= 655749 
 
-- Cooling Device speed decreased below Upper non-critical threshold Cleared 
trapCoolingDeviceOverSpeedWarningLowCleared TRAP-TYPE 
ENTERPRISE petevts 
DESCRIPTION  
"Cooling Device Over Speed Warning (Upper non-critical, going low) Cleared" 

--#TYPE       "Cooling Device Event" 
--#SUMMARY    "Cooling Device Over Speed Warning (Upper non-critical, going low) Cleared" 
--#ARGUMENTS  {} 
--#SEVERITY   INFORMATIONAL 

::= 655750 
 
-- Cooling Device speed increased above upper non-critical threshold Cleared 
trapCoolingDeviceOverSpeedWarningHighCleared TRAP-TYPE 
ENTERPRISE petevts 
DESCRIPTION  
"Cooling Device Over Speed Warning (Upper non-critical, going high)Cleared" 

--#TYPE       "Cooling Device Event" 
--#SUMMARY    "Cooling Device Over Speed Warning (Upper non-critical, going high)Cleared" 
--#ARGUMENTS  {} 
--#SEVERITY   INFORMATIONAL 

::= 655751 
 
-- Cooling Device speed decreased below Upper critical threshold Cleared 
trapCoolingDeviceOverSpeedCriticalLowCleared TRAP-TYPE 
ENTERPRISE petevts 
DESCRIPTION  
"Critical Cooling Device Over Speed problem (Upper critical, going low) Cleared" 

--#TYPE       "Cooling Device Event" 
--#SUMMARY    "Cooling Device Over Speed Warning (Upper critical, going low) Cleared" 
--#ARGUMENTS  {} 
--#SEVERITY   INFORMATIONAL 

::= 655752 
 
 -- Cooling Device speed increased above Upper critical threshold Cleared 
trapCoolingDeviceOverSpeedCriticalHighCleared TRAP-TYPE 
ENTERPRISE petevts 
DESCRIPTION  
"Critical Cooling Device Over Speed problem (Upper critical, going high)Cleared" 

--#TYPE       "Cooling Device Event" 
--#SUMMARY    "Cooling Device Over Speed Warning (Upper critical, going high)Cleared" 
--#ARGUMENTS  {} 
--#SEVERITY   INFORMATIONAL 

::= 655753 
 
 -- Cooling Device speed decreased below Upper non-recoverable threshold Cleared 
trapCoolingDeviceOverSpeedNonRecoverableLowCleared TRAP-TYPE 
ENTERPRISE petevts 
DESCRIPTION  
"Critical Cooling Device Over Speed problem (Upper non-recoverable, going low)Cleared" 

--#TYPE       "Cooling Device Event" 
--#SUMMARY    "Cooling Device Over Speed Warning (Upper non-recoverable, going low)Cleared" 
--#ARGUMENTS  {} 
--#SEVERITY   INFORMATIONAL 

::= 655754 
 
 -- Cooling Device speed increased above Upper non-recoverable threshold Cleared 
trapCoolingDeviceOverSpeedNonRecoverableHighCleared TRAP-TYPE 
ENTERPRISE petevts 
DESCRIPTION  
"Critical Cooling Device Over Speed problem (Upper non-recoverable, going high) Cleared" 

--#TYPE       "Cooling Device Event" 
--#SUMMARY    "Cooling Device Under Speed Warning (Upper non-recoverable, going high) Cleared" 
--#ARGUMENTS  {} 
--#SEVERITY   INFORMATIONAL 

::= 655755 
 
 -- Cooling Device Removed/Absent 
trapCoolingDeviceRemoved TRAP-TYPE 
ENTERPRISE petevts 
DESCRIPTION  
 "Cooling Device Removed/Absent" 

--#TYPE       "Cooling Device Event" 
--#SUMMARY    "Cooling Device Removed/Absent" 
--#ARGUMENTS  {} 
--#SEVERITY   CRITICAL 

::= 657408 
 
  -- Cooling Device Inserted/Present 
trapCoolingDeviceInserted TRAP-TYPE 
ENTERPRISE petevts 
DESCRIPTION  
 "Cooling Device Inserted/Present" 

--#TYPE       "Cooling Device Event" 
--#SUMMARY    "Cooling Device Inserted/Present" 
--#ARGUMENTS  {} 
--#SEVERITY   INFORMATIONAL 

::= 657409 
 
-- Cooling Device Full Redundancy  
trapCoolingDeviceFullRedundancy TRAP-TYPE 
ENTERPRISE petevts 
DESCRIPTION  
 "Cooling Device redundancy has returned to Normal" 

--#TYPE       "Cooling Device Event" 
--#SUMMARY    "Cooling Device redundancy has returned to Normal" 
--#ARGUMENTS  {} 
--#SEVERITY   INFORMATIONAL 

::= 658176 

-- Cooling Device Redundancy lost  
trapCoolingDeviceRedundancyLost TRAP-TYPE 
ENTERPRISE petevts 
DESCRIPTION  
 "Cooling Device Redundancy has been Lost" 

--#TYPE       "Cooling Device Event" 
--#SUMMARY    "Cooling Device Redundancy has been Lost" 
--#ARGUMENTS  {} 
--#SEVERITY   CRITICAL 

::= 658177 

-- Cooling Device Redundancy degraded 
trapCoolingDeviceRedundancyDegraded TRAP-TYPE 
ENTERPRISE petevts 
DESCRIPTION  
 "Cooling Device Redundancy is in a degraded state" 

--#TYPE       "Cooling Device Event" 
--#SUMMARY    "Cooling Device Redundancy is in a degraded state" 
--#ARGUMENTS  {} 
--#SEVERITY   WARNING 

::= 658178 
 

-- ********************************************** 
-- *		Memory			* 
-- ********************************************** 

-- Memory Predictive Failure state has been cleared 
trapMemoryPredictiveFailureDeasserted TRAP-TYPE 
ENTERPRISE petevts 
DESCRIPTION  
 "Memory Predictive Failure state has been cleared" 

--#TYPE       "Memory Event" 
--#SUMMARY    "Memory Predictive Failure state has been cleared." 
--#ARGUMENTS  {} 
--#SEVERITY   INFORMATIONAL 

::= 787456 
 
-- Memory Predictive Failure state has been asserted 
trapMemoryPredictiveFailureAsserted TRAP-TYPE 
ENTERPRISE petevts 
DESCRIPTION  
 "Memory Predictive Failure state has been asserted" 

--#TYPE       "Memory Event" 
--#SUMMARY    "Memory Predictive Failure has been asserted." 
--#ARGUMENTS  {} 
--#SEVERITY   CRITICAL 

::= 787457 

-- Correctable ECC or other correctable memory error detected. 
trapMemoryCorrectableEccError TRAP-TYPE 
ENTERPRISE petevts 
DESCRIPTION 
 "Correctable ECC or other correctable memory error detected." 

--#TYPE       "Memory Event" 
--#SUMMARY    "Correctable ECC or other correctable memory error detected." 
--#ARGUMENTS  {} 
--#SEVERITY   INFORMATIONAL 

::= 814848 
 
-- Uncorrectable ECC or other uncorrectable memory error detected 
trapMemoryUncorrectableEccError TRAP-TYPE 
ENTERPRISE petevts 
DESCRIPTION 
 "Uncorrectable ECC or other uncorrectable memory error detected." 

--#TYPE       "Memory Event" 
--#SUMMARY    "Uncorrectable ECC or other uncorrectable memory error detected." 
--#ARGUMENTS  {} 
--#SEVERITY   INFORMATIONAL 

::= 814849 

 -- Parity error detected. 
trapMemoryParityError TRAP-TYPE 
ENTERPRISE petevts 
DESCRIPTION 
 "Parity error detected." 

--#TYPE       "Memory Event" 
--#SUMMARY    "Parity error detected." 
--#ARGUMENTS  {} 
--#SEVERITY   INFORMATIONAL 

::= 814850 
 
-- Memory Scrub Failed 
trapMemoryScrubFailed TRAP-TYPE 
ENTERPRISE petevts 
DESCRIPTION 
 "Memory Scrub Failed" 

--#TYPE       "Memory Event" 
--#SUMMARY    "Memory Scrub Failed" 
--#ARGUMENTS  {} 
--#SEVERITY   INFORMATIONAL 

::= 814851 
 
-- Memory Device Disabled 
trapMemoryDeviceDisabled TRAP-TYPE 
ENTERPRISE petevts 
DESCRIPTION 
 "Memory Device Disabled." 

--#TYPE       "Memory Event" 
--#SUMMARY    "Memory Device Disabled." 
--#ARGUMENTS  {} 
--#SEVERITY   INFORMATIONAL 

::= 814852 
 
 -- Correctable ECC / other correctable memory error logging limit reached 
trapMemoryCorrectableECC TRAP-TYPE 
ENTERPRISE petevts 
DESCRIPTION 
 "Correctable ECC / other correctable memory error logging limit reached" 

--#TYPE       "Memory Event" 
--#SUMMARY    "Correctable ECC / other correctable memory error logging limit reached" 
--#ARGUMENTS  {} 
--#SEVERITY   INFORMATIONAL 

::= 814853 
 
-- Memory Presence detected 
trapMemoryPresenceDetectedAssert TRAP-TYPE 
ENTERPRISE petevts 
DESCRIPTION 
 "Memory Presence detected." 

--#TYPE       "Memory Event" 
--#SUMMARY    "Memory Presence detected." 
--#ARGUMENTS  {} 
--#SEVERITY   INFORMATIONAL 

::= 814854 
 
 -- Configuration Error 
trapMemoryConfigurationError TRAP-TYPE 
ENTERPRISE petevts 
DESCRIPTION 
 "Memory Configuration Error detected." 

--#TYPE       "Memory Event" 
--#SUMMARY    "Memory Configuration Error  detected." 
--#ARGUMENTS  {} 
--#SEVERITY   INFORMATIONAL 

::= 814855 
 
-- Spare Unit of Memory detected 
trapMemorySpareUnit TRAP-TYPE 
ENTERPRISE petevts 
DESCRIPTION 
 "Spare Unit of Memory detected" 

--#TYPE       "Memory Event" 
--#SUMMARY    "Spare Unit of Memory detected" 
--#ARGUMENTS  {} 
--#SEVERITY   INFORMATIONAL 

::= 814856 
 
-- Memory Automatically Throttled 
trapMemoryAutomaticallyThrottled TRAP-TYPE 
ENTERPRISE petevts 
DESCRIPTION 
 "Memory Automatically Throttled" 

--#TYPE       "Memory Event" 
--#SUMMARY    "Memory Automatically Throttled" 
--#ARGUMENTS  {} 
--#SEVERITY   INFORMATIONAL 

::= 814857 
 
-- Critical Overtemperature 
trapMemoryCriticalOvertemperature TRAP-TYPE 
ENTERPRISE petevts 
DESCRIPTION 
 "Memory event - Critical Overtemperature" 

--#TYPE       "Memory Event" 
--#SUMMARY    "Memory event - Critical Overtemperature" 
--#ARGUMENTS  {} 
--#SEVERITY   INFORMATIONAL 

::= 814858 
 
-- Correctable ECC or other correctable memory error cleared. 
trapMemoryCorrectableEccErrorCleared TRAP-TYPE 
ENTERPRISE petevts 
DESCRIPTION 
 "Correctable ECC or other correctable memory error cleared." 

--#TYPE       "Memory Event" 
--#SUMMARY    "Correctable ECC or other correctable memory error cleared." 
--#ARGUMENTS  {} 
--#SEVERITY   INFORMATIONAL 

::= 814976 
 
-- Uncorrectable ECC or other uncorrectable memory error cleared 
trapMemoryUncorrectableEccErrorCleared TRAP-TYPE 
ENTERPRISE petevts 
DESCRIPTION 
 "Uncorrectable ECC or other uncorrectable memory error Cleared." 

--#TYPE       "Memory Event" 
--#SUMMARY    "Uncorrectable ECC or other uncorrectable memory error Cleared." 
--#ARGUMENTS  {} 
--#SEVERITY   INFORMATIONAL 

::= 814977 
 
 -- Parity error Cleared. 
trapMemoryParityErrorCleared TRAP-TYPE 
ENTERPRISE petevts 
DESCRIPTION 
 "Parity error Cleared." 

--#TYPE       "Memory Event" 
--#SUMMARY    "Parity error Cleared." 
--#ARGUMENTS  {} 
--#SEVERITY   INFORMATIONAL 

::= 814978 
 
-- Memory Scrub Failure Cleared 
trapMemoryScrubFailureCleared TRAP-TYPE 
ENTERPRISE petevts 
DESCRIPTION 
 "Memory Scrub Failure Cleared" 

--#TYPE       "Memory Event" 
--#SUMMARY    "Memory Scrub Failure Cleared" 
--#ARGUMENTS  {} 
--#SEVERITY   INFORMATIONAL 

::= 814979 
 
-- Memory Device Enabled 
trapMemoryDeviceEnabled TRAP-TYPE 
ENTERPRISE petevts 
DESCRIPTION 
 "Memory Device Enabled." 

--#TYPE       "Memory Event" 
--#SUMMARY    "Memory Device Enabled." 
--#ARGUMENTS  {} 
--#SEVERITY   INFORMATIONAL 

::= 814980 
 
 -- Correctable ECC / other correctable memory error logging limit reached Cleared 
trapMemoryCorrectableECCCleared TRAP-TYPE 
ENTERPRISE petevts 
DESCRIPTION 
 "Correctable ECC / other correctable memory error logging limit reached Cleared" 

--#TYPE       "Memory Event" 
--#SUMMARY    "Correctable ECC / other correctable memory error logging limit reached Cleared" 
--#ARGUMENTS  {} 
--#SEVERITY   INFORMATIONAL 

::= 814981 
 
-- Memory Presence detected Deassert 
trapMemoryPresenceNotDetected TRAP-TYPE 
ENTERPRISE petevts 
DESCRIPTION 
 "Memory Presence Not detected" 

--#TYPE       "Memory Event" 
--#SUMMARY    "Memory Presence not detected" 
--#ARGUMENTS  {} 
--#SEVERITY   INFORMATIONAL 

::= 814982 
 
 -- Configuration Error Cleared 
trapMemoryConfigurationErrorCleared TRAP-TYPE 
ENTERPRISE petevts 
DESCRIPTION 
 "Memory Configuration Error Cleared." 

--#TYPE       "Memory Event" 
--#SUMMARY    "Memory Configuration Error  Cleared." 
--#ARGUMENTS  {} 
--#SEVERITY   INFORMATIONAL 

::= 814983 
 
-- Spare Unit of Memory detected Deassert 
trapMemorySpareUnitDeassert TRAP-TYPE 
ENTERPRISE petevts 
DESCRIPTION 
 "Spare Unit of Memory detected Deassert" 

--#TYPE       "Memory Event" 
--#SUMMARY    "Spare Unit of Memory detected Deassert" 
--#ARGUMENTS  {} 
--#SEVERITY   INFORMATIONAL 

::= 814984 
 
-- Memory Automatically Throttled Cleared 
trapMemoryAutomaticallyThrottledCleared TRAP-TYPE 
ENTERPRISE petevts 
DESCRIPTION 
 "Memory Automatically Throttled Cleared" 

--#TYPE       "Memory Event" 
--#SUMMARY    "Memory Automatically Throttled Cleared" 
--#ARGUMENTS  {} 
--#SEVERITY   INFORMATIONAL 

::= 814985 
 
-- Critical Overtemperature Cleared 
trapMemoryCriticalOvertemperatureCleared TRAP-TYPE 
ENTERPRISE petevts 
DESCRIPTION 
 "Memory event - Critical Overtemperature Cleared" 

--#TYPE       "Memory Event" 
--#SUMMARY    "Memory event - Critical Overtemperature Cleared"s 
--#ARGUMENTS  {} 
--#SEVERITY   INFORMATIONAL 

::= 814986 
 
-- ********************************************** 
-- *		Drive Slot (Bay)			* 
-- ********************************************** 
-- Hard Disk Drive Fault Sensor event 
trapDriveSlotPredictiveFailureDeasserted TRAP-TYPE 
ENTERPRISE petevts 
DESCRIPTION  
 "This state indicates that a HDD Fault LED which was ON before is OFF now." 

--#TYPE       "Drive Slot Event" 
--#SUMMARY    "Hard Disk Drive Fault LED is OFF." 
--#ARGUMENTS  {} 
--#SEVERITY   INFORMATIONAL 

::= 852992 
 
-- Hard Disk Drive Fault Sensor event 
trapDriveSlotPredictiveFailureAsserted TRAP-TYPE 
ENTERPRISE petevts 
DESCRIPTION  
 "A HDD Fault LED is ON." 

--#TYPE       "Drive Slot Event" 
--#SUMMARY    "Hard Disk Drive Fault LED is ON." 
--#ARGUMENTS  {} 
--#SEVERITY   MAJOR 

::= 852993 


-- Hard Disk Drive Presence Sensor event 
trapDriveSlotDriveRemovedOrAbsent TRAP-TYPE 
ENTERPRISE petevts 
DESCRIPTION 
 "Hard Disk Drive is absent or has been removed." 

--#TYPE         "Drive Slot Event" 
--#SUMMARY      "Hard Disk Drive is absent or has been removed." 
--#ARGUMENTS    {} 
--#SEVERITY     INFORMATIONAL 

::= 880512
-- Change from 880384 to 880512 for Insert Alert Absent, Remove Alert Present 20141010<<>>
 
-- Hard Disk Drive Fault 
trapDriveSlotDriveFault TRAP-TYPE 
ENTERPRISE petevts 
DESCRIPTION 
 "Hard Disk Drive Fault" 

--#TYPE         "Drive Slot Event" 
--#SUMMARY      "Hard Disk Drive Fault" 
--#ARGUMENTS    {} 
--#SEVERITY     CRITICAL 

::= 880385 
 
-- Hard Disk Drive Predictive Failure 
trapDriveSlotPredictiveFailure TRAP-TYPE 
ENTERPRISE petevts 
DESCRIPTION 
 "Hard Disk Drive Predictive Failure" 

--#TYPE         "Drive Slot Event" 
--#SUMMARY      "Hard Disk Drive Predictive Failure" 
--#ARGUMENTS    {} 
--#SEVERITY     INFORMATIONAL 

::= 880386 
 
-- Hard Disk Drive Hot Spare (Ready to Remove) 
trapDriveSlotHotSpare TRAP-TYPE 
ENTERPRISE petevts 
DESCRIPTION 
  " Hard Disk Drive Hot Spare (Ready to remove) Asserted " 

--#TYPE         "Drive Slot Event" 
--#SUMMARY      "Hard Disk Drive Hot spare (Ready to Remove) " 
--#ARGUMENTS    {} 
--#SEVERITY     INFORMATIONAL 

::= 880387 
 
-- Hard Disk Drive Consistency Check / Parity Check in progress 
trapDriveSlotConsistencyCheckInProgress TRAP-TYPE 
ENTERPRISE petevts 
DESCRIPTION 
 "Hard Disk Drive Consistency Check / Parity Check in progress" 

--#TYPE         "Drive Slot Event" 
--#SUMMARY      "Hard Disk Drive Consistency Check / Parity Check in progress" 
--#ARGUMENTS    {} 
--#SEVERITY     INFORMATIONAL 

::= 880388 
 
-- Hard Disk Drive In Critical Array 
trapDriveSlotInCriticalArray TRAP-TYPE 
ENTERPRISE petevts 
DESCRIPTION 
 "Hard Disk Drive In Critical Array" 

--#TYPE         "Drive Slot Event" 
--#SUMMARY      "Hard Disk Drive In Critical Array" 
--#ARGUMENTS    {} 
--#SEVERITY     INFORMATIONAL 

::= 880389 
 
-- Hard Disk Drive In Failed Array 
trapDriveSlotInFailedArray TRAP-TYPE 
ENTERPRISE petevts 
DESCRIPTION 
 "Hard Disk Drive In Failed Array" 

--#TYPE         "Drive Slot Event" 
--#SUMMARY      "Hard Disk Drive In Failed Array" 
--#ARGUMENTS    {} 
--#SEVERITY     CRITICAL 

::= 880390 
 
-- Hard Disk Drive Rebuild/Remap in progress 
trapDriveSlotRebuildOrRemapInProgress TRAP-TYPE 
ENTERPRISE petevts 
DESCRIPTION 
 "Hard Disk Drive Rebuild/Remap in progress" 

--#TYPE         "Drive Slot Event" 
--#SUMMARY      "Hard Disk Drive Rebuild/Remap in progress" 
--#ARGUMENTS    {} 
--#SEVERITY     INFORMATIONAL 

::= 880391 
 
-- Hard Disk Drive Rebuild/Remap Aborted 
trapDriveSlotRebuildOrRemapAborted TRAP-TYPE 
ENTERPRISE petevts 
DESCRIPTION 
 "Hard Disk Drive Rebuild/Remap Aborted" 

--#TYPE         "Drive Slot Event" 
--#SUMMARY      "Hard Disk Drive Rebuild/Remap Aborted" 
--#ARGUMENTS    {} 
--#SEVERITY     INFORMATIONAL 

::= 880392 
 

-- Drive Presence Sensor event 
trapDriveSlotDriveInsertedOrPresent TRAP-TYPE 
ENTERPRISE petevts 
DESCRIPTION 
 "Hard Disk Drive is present or has been inserted." 

--#TYPE         "Drive Slot Event" 
--#SUMMARY      "Hard Disk Drive is present or has been inserted." 
--#ARGUMENTS    {} 
--#SEVERITY     INFORMATIONAL 


::= 880384 
-- Change from 880512 to 880384 for Insert Alert Absent, Remove Alert Present 20141010<<>>

-- Hard Disk Drive Fault Cleared 
trapDriveSlotDriveFaultCleared TRAP-TYPE 
ENTERPRISE petevts 
DESCRIPTION 
 "Hard Disk Drive Fault Cleared" 

--#TYPE         "Drive Slot Event" 
--#SUMMARY      "Hard Disk Drive Fault Cleared" 
--#ARGUMENTS    {} 
--#SEVERITY     INFORMATIONAL 

::= 880513 
 
-- Hard Disk Drive Predictive Failure Cleared 
trapDriveSlotPredictiveFailureCleared TRAP-TYPE 
ENTERPRISE petevts 
DESCRIPTION 
 "Hard Disk Drive Predictive Failure Cleared" 

--#TYPE         "Drive Slot Event" 
--#SUMMARY      "Hard Disk Drive Predictive Failure Cleared" 
--#ARGUMENTS    {} 
--#SEVERITY     INFORMATIONAL 

::= 880514 
 
-- Hard Disk Drive Hot Spare 
trapDriveSlotHotSpareDeasserted TRAP-TYPE 
ENTERPRISE petevts 
DESCRIPTION 
 "Hard Disk Drive Hot Spare Deasserted" 

--#TYPE         "Drive Slot Event" 
--#SUMMARY      "Hard Disk Drive Hot spare" 
--#ARGUMENTS    {} 
--#SEVERITY     INFORMATIONAL 

::= 880515 
 
-- Hard Disk Drive Consistency Check / Parity Check in progress Deasserted 
trapDriveSlotConsistencyCheckInProgressDeasserted TRAP-TYPE 
ENTERPRISE petevts 
DESCRIPTION 
 "Hard Disk Drive Consistency Check / Parity Check in progress Deasserted" 

--#TYPE         "Drive Slot Event" 
--#SUMMARY      "Hard Disk Drive Consistency Check / Parity Check in progress Deasserted" 
--#ARGUMENTS    {} 
--#SEVERITY     INFORMATIONAL 

::= 880516 
 
-- Hard Disk Drive In Critical Array Deasserted 
trapDriveSlotInCriticalArrayDeasserted TRAP-TYPE 
ENTERPRISE petevts 
DESCRIPTION 
 "Hard Disk Drive In Critical Array Deasserted" 

--#TYPE         "Drive Slot Event" 
--#SUMMARY      "Hard Disk Drive In Critical Array Deasserted" 
--#ARGUMENTS    {} 
--#SEVERITY     INFORMATIONAL 

::= 880517 
 
-- Hard Disk Drive In Failed Array Deasserted 
trapDriveSlotInFailedArrayDeasserted TRAP-TYPE 
ENTERPRISE petevts 
DESCRIPTION 
 "Hard Disk Drive In Failed Array Deasserted" 

--#TYPE         "Drive Slot Event" 
--#SUMMARY      "Hard Disk Drive In Failed Array Deasserted" 
--#ARGUMENTS    {} 
--#SEVERITY     CRITICAL 

::= 880518 
 
-- Hard Disk Drive Rebuild/Remap in progress Deasserted 
trapDriveSlotRebuildOrRemapInProgressDeasserted TRAP-TYPE 
ENTERPRISE petevts 
DESCRIPTION 
 "Hard Disk Drive Rebuild/Remap in progress Deasserted(completed)" 

--#TYPE         "Drive Slot Event" 
--#SUMMARY      "Hard Disk Drive Rebuild/Remap in progress Deasserted(completed)" 
--#ARGUMENTS    {} 
--#SEVERITY     INFORMATIONAL 

::= 880519 
 
-- Hard Disk Drive Rebuild/Remap Aborted Deasserted(completed) 
trapDriveSlotRebuildOrRemapAbortedDeasserted TRAP-TYPE 
ENTERPRISE petevts 
DESCRIPTION 
 "Hard Disk Drive Rebuild/Remap Aborted Deasserted" 

--#TYPE         "Drive Slot Event" 
--#SUMMARY      "Hard Disk Drive Rebuild/Remap Aborted Deasserted(completed)" 
--#ARGUMENTS    {} 
--#SEVERITY     INFORMATIONAL 

::= 880520 

-- ********************************************** 
-- *		POST Memory Resize			* 
-- ********************************************** 

-- POST Memory Resize Failure Deasserted 
trapPOSTMemoryResizeFailureDeasserted TRAP-TYPE 
ENTERPRISE petevts 
DESCRIPTION  
 "POST Memory Resize Failure Deasserted" 

--#TYPE       "POST Memory Resize Event" 
--#SUMMARY    "POST Memory Resize Failure Deasserted" 
--#ARGUMENTS  {} 
--#SEVERITY   INFORMATIONAL 

::= 918528 
 
-- POST Memory Resize Failure Asserted 
trapPOSTMemoryResizeFailureAsserted TRAP-TYPE 
ENTERPRISE petevts 
DESCRIPTION  
 "POST Memory Resize Failure Asserted" 

--#TYPE       "POST Memory Resize Event" 
--#SUMMARY    "POST Memory Resize Failure Asserted" 
--#ARGUMENTS  {} 
--#SEVERITY   MAJOR 

::= 918529 


-- ********************************************** 
-- *		System Firmware Progress			* 
-- ********************************************** 

-- Power On Self Test (POST) code error 
trapBIOSPOSTCodeError TRAP-TYPE 
ENTERPRISE petevts 
DESCRIPTION  
 "System Firmware Progress: BIOS POST code error" 

--#TYPE       "System Firmware Progress Event" 
--#SUMMARY    "System Firmware Progress: BIOS POST code error" 
--#ARGUMENTS  {} 
--#SEVERITY   CRITICAL 

::= 1011456 

-- System Firmware Hang 
trapSystemFirmwareHang TRAP-TYPE 
ENTERPRISE petevts 
DESCRIPTION  
 "System Firmware Hang" 

--#TYPE       "System Firmware Progress Event" 
--#SUMMARY    "System Firmware Hang" 
--#ARGUMENTS  {} 
--#SEVERITY   CRITICAL 

::= 1011457 
 
-- System Firmware Progress 
trapSystemFirmwareProgress TRAP-TYPE 
ENTERPRISE petevts 
DESCRIPTION  
 "System Firmware Progress" 

--#TYPE       "System Firmware Progress Event" 
--#SUMMARY    "System Firmware Progress" 
--#ARGUMENTS  {} 
--#SEVERITY   INFORMATIONAL 

::= 1011458 

-- Power On Self Test (POST) code error Cleared 
trapBIOSPOSTCodeErrorCleared TRAP-TYPE 
ENTERPRISE petevts 
DESCRIPTION  
 "System Firmware Progress: BIOS POST code error Cleared" 

--#TYPE       "System Firmware Progress Event" 
--#SUMMARY    "System Firmware Progress: BIOS POST code error Cleared" 
--#ARGUMENTS  {} 
--#SEVERITY   INFORMATIONAL 

::= 1011584 

-- System Firmware Hang Cleared 
trapSystemFirmwareHangCleared TRAP-TYPE 
ENTERPRISE petevts 
DESCRIPTION  
 "System Firmware Hang Cleared" 

--#TYPE       "System Firmware Progress Event" 
--#SUMMARY    "System Firmware Hang Cleared" 
--#ARGUMENTS  {} 
--#SEVERITY   INFORMATIONAL 

::= 1011585 
 
-- System Firmware Progress Completed  
trapSystemFirmwareProgressCompleted TRAP-TYPE 
ENTERPRISE petevts 
DESCRIPTION  
 "System Firmware Progress Completed " 

--#TYPE       "System Firmware Progress Event" 
--#SUMMARY    "System Firmware Progress Completed " 
--#ARGUMENTS  {} 
--#SEVERITY   INFORMATIONAL 

::= 1011586 

-- ********************************************** 
-- *		Event Logging Disabled			* 
-- ********************************************** 

-- Correctable Memory Error Logging Disabled 
trapCorrectableMemoryErrorLoggingDisabled TRAP-TYPE 
ENTERPRISE petevts 
DESCRIPTION  
 "Correctable Memory Error Logging Disabled" 

--#TYPE       "System Event Log" 
--#SUMMARY    "Correctable Memory Error Logging Disabled" 
--#ARGUMENTS  {} 
--#SEVERITY   INFORMATIONAL 

::= 1076992 

-- Event Type Logging Disabled. 
trapEventTypeLoggingDisabled TRAP-TYPE 
ENTERPRISE petevts 
DESCRIPTION  
 "Event Type Logging Disabled" 

--#TYPE       "System Event Log" 
--#SUMMARY    "Event Type Logging Disabled." 
--#ARGUMENTS  {} 
--#SEVERITY   INFORMATIONAL 

::= 1076993 

-- SEL Area Reset/Cleared 
trapSELAreaResetOrCleared TRAP-TYPE 
ENTERPRISE petevts 
DESCRIPTION  
 "SEL Area Reset/Cleared" 

--#TYPE       "System Event Log" 
--#SUMMARY    "SEL Area Reset/Cleared" 
--#ARGUMENTS  {} 
--#SEVERITY   INFORMATIONAL 

::= 1076994 

-- All Event Logging Disabled 
trapEventLoggingDisabled TRAP-TYPE 
ENTERPRISE petevts 
DESCRIPTION  
 "System Event Logging Disabled" 

--#TYPE       "System Event Log" 
--#SUMMARY    "System Event Logging Disabled" 
--#ARGUMENTS  {} 
--#SEVERITY   CRITICAL 

::= 1076995 

-- SEL Full 
trapSelFull TRAP-TYPE 
ENTERPRISE petevts 
DESCRIPTION 
 "SEL Full." 

--#TYPE       "System Event Log" 
--#SUMMARY    "SEL Full." 
--#ARGUMENTS  {} 
--#SEVERITY   INFORMATIONAL 

::= 1076996 

 -- SEL Almost Full 
trapSelAlmostFull TRAP-TYPE 
ENTERPRISE petevts 
DESCRIPTION 
 "SEL Almost Full." 

--#TYPE       "System Event Log" 
--#SUMMARY    "SEL Almost Full." 
--#ARGUMENTS  {} 
--#SEVERITY   INFORMATIONAL 

::= 1076997 
 
-- Correctable Machine Check Error Logging Disabled 
trapCorrectableMachineCheckErrorLoggingDisabled TRAP-TYPE 
ENTERPRISE petevts 
DESCRIPTION 
 "Correctable Machine Check Error Logging Disabled" 

--#TYPE       "System Event Log" 
--#SUMMARY    "Correctable Machine Check Error Logging Disabled" 
--#ARGUMENTS  {} 
--#SEVERITY   INFORMATIONAL 

::= 1076998 
 
 
-- Correctable Memory Error Logging Enabled 
trapCorrectableMemoryErrorLoggingEnabled TRAP-TYPE 
ENTERPRISE petevts 
DESCRIPTION  
 "Correctable Memory Error Logging Enabled" 

--#TYPE       "System Event Log" 
--#SUMMARY    "Correctable Memory Error Logging Enabled" 
--#ARGUMENTS  {} 
--#SEVERITY   INFORMATIONAL 

::= 1077120 

-- Event Type Logging Enabled. 
trapEventTypeLoggingEnabled TRAP-TYPE 
ENTERPRISE petevts 
DESCRIPTION  
 "Event Type Logging Enabled" 

--#TYPE       "System Event Log" 
--#SUMMARY    "Event Type Logging Enabled." 
--#ARGUMENTS  {} 
--#SEVERITY   INFORMATIONAL 

::= 1077121 

-- SEL Area Reset/Cleared Event Deasserted 
trapSELAreaResetOrClearedEventDeassert TRAP-TYPE 
ENTERPRISE petevts 
DESCRIPTION  
 "SEL Area Reset/Cleared" 

--#TYPE       "System Event Log" 
--#SUMMARY    "SEL Area Reset/Cleared Event Deasserted" 
--#ARGUMENTS  {} 
--#SEVERITY   INFORMATIONAL 

::= 1077122 

-- All Event Logging Enabled 
trapEventLoggingEnabled TRAP-TYPE 
ENTERPRISE petevts 
DESCRIPTION  
 "System Event Logging Enabled" 

--#TYPE       "System Event Log" 
--#SUMMARY    "System Event Logging Enabled" 
--#ARGUMENTS  {} 
--#SEVERITY   INFORMATIONAL 

::= 1077123 

-- SEL Full Event Cleared 
trapSelFullEventCleared TRAP-TYPE 
ENTERPRISE petevts 
DESCRIPTION 
 "SEL Full Event Cleared" 

--#TYPE       "System Event Log" 
--#SUMMARY    "SEL Full Event Cleared" 
--#ARGUMENTS  {} 
--#SEVERITY   INFORMATIONAL 

::= 1077124 

 -- SEL Almost Full Event Cleared 
trapSelAlmostFullEventCleared TRAP-TYPE 
ENTERPRISE petevts 
DESCRIPTION 
 "SEL Almost Full Event Cleared" 

--#TYPE       "System Event Log" 
--#SUMMARY    "SEL Almost Full Event Cleared" 
--#ARGUMENTS  {} 
--#SEVERITY   INFORMATIONAL 

::= 1077125 
 
-- Correctable Machine Check Error Logging Enabled 
trapCorrectableMachineCheckErrorLoggingEnabled TRAP-TYPE 
ENTERPRISE petevts 
DESCRIPTION 
 "Correctable Machine Check Error Logging Enabled" 

--#TYPE       "System Event Log" 
--#SUMMARY    "Correctable Machine Check Error Logging Enabled" 
--#ARGUMENTS  {} 
--#SEVERITY   INFORMATIONAL 

::= 1077126 

-- ********************************************** 
-- *		WatchDog1			* 
-- ********************************************** 
-- BIOS Watchdog Reset 
trapBIOSWatchdogReset TRAP-TYPE 
ENTERPRISE petevts 
DESCRIPTION 
 "BIOS Watchdog Reset" 

--#TYPE       "Watchdog Event" 
--#SUMMARY    "BIOS Watchdog Reset" 
--#ARGUMENTS  {} 
--#SEVERITY   INFORMATIONAL 

::= 1142528 

-- OS Watchdog Reset 
trapOSWatchdogReset TRAP-TYPE 
ENTERPRISE petevts 
DESCRIPTION 
 "OS Watchdog Reset" 

--#TYPE       "Watchdog Event" 
--#SUMMARY    "OS Watchdog Reset" 
--#ARGUMENTS  {} 
--#SEVERITY   INFORMATIONAL 

::= 1142529 
 
-- OS Watchdog Shut Down 
trapOSWatchdogShutDown TRAP-TYPE 
ENTERPRISE petevts 
DESCRIPTION 
 "OS Watchdog Shut Down" 

--#TYPE       "Watchdog Event" 
--#SUMMARY    "OS Watchdog Shut Down" 
--#ARGUMENTS  {} 
--#SEVERITY   INFORMATIONAL 

::= 1142530 
 
-- OS Watchdog Power Down 
trapOSWatchdogPowerDown TRAP-TYPE 
ENTERPRISE petevts 
DESCRIPTION 
 "OS Watchdog Power Down" 

--#TYPE       "Watchdog Event" 
--#SUMMARY    "OS Watchdog Power Down" 
--#ARGUMENTS  {} 
--#SEVERITY   INFORMATIONAL 

::= 1142531 
 
-- OS Watchdog Power Cycle 
trapOSWatchdogPowerCycle TRAP-TYPE 
ENTERPRISE petevts 
DESCRIPTION 
 "OS Watchdog Power Cycle" 

--#TYPE       "Watchdog Event" 
--#SUMMARY    "OS Watchdog Power Cycle" 
--#ARGUMENTS  {} 
--#SEVERITY   INFORMATIONAL 

::= 1142532 
 
-- OS Watchdog NMI / Diagnostic Interrupt 
trapOSWatchdogNMIOrDiagnosticInterrupt TRAP-TYPE 
ENTERPRISE petevts 
DESCRIPTION 
 "OS Watchdog NMI / Diagnostic Interrupt" 

--#TYPE       "Watchdog Event" 
--#SUMMARY    "OS Watchdog NMI / Diagnostic Interrupt" 
--#ARGUMENTS  {} 
--#SEVERITY   INFORMATIONAL 

::= 1142533 
 
-- OS Watchdog Expired, status only 
trapOSWatchdogExpired TRAP-TYPE 
ENTERPRISE petevts 
DESCRIPTION 
 "OS Watchdog Expired, status only" 

--#TYPE       "Watchdog Event" 
--#SUMMARY    "OS Watchdog Expired, status only" 
--#ARGUMENTS  {} 
--#SEVERITY   INFORMATIONAL 

::= 1142534 
 
-- OS Watchdog pre-timeout Interrupt, non-NMI 
trapOSWatchdogPreTimeoutInterrupt TRAP-TYPE 
ENTERPRISE petevts 
DESCRIPTION 
 "OS Watchdog pre-timeout Interrupt, non-NMI" 

--#TYPE       "Watchdog Event" 
--#SUMMARY    "OS Watchdog pre-timeout Interrupt, non-NMI" 
--#ARGUMENTS  {} 
--#SEVERITY   INFORMATIONAL 

::= 1142535 
 
-- BIOS Watchdog Reset Deasserted 
trapBIOSWatchdogResetDeasserted TRAP-TYPE 
ENTERPRISE petevts 
DESCRIPTION 
 "BIOS Watchdog Reset Deasserted" 

--#TYPE       "Watchdog Event" 
--#SUMMARY    "BIOS Watchdog Reset Deasserted" 
--#ARGUMENTS  {} 
--#SEVERITY   INFORMATIONAL 

::= 1142656 

-- OS Watchdog Reset Deasserted 
trapOSWatchdogResetDeasserted TRAP-TYPE 
ENTERPRISE petevts 
DESCRIPTION 
 "OS Watchdog Reset Deasserted" 

--#TYPE       "Watchdog Event" 
--#SUMMARY    "OS Watchdog Reset Deasserted" 
--#ARGUMENTS  {} 
--#SEVERITY   INFORMATIONAL 

::= 1142657 
 
-- OS Watchdog Shut Down Deasserted 
trapOSWatchdogShutDownDeasserted TRAP-TYPE 
ENTERPRISE petevts 
DESCRIPTION 
 "OS Watchdog Shut Down Deasserted" 

--#TYPE       "Watchdog Event" 
--#SUMMARY    "OS Watchdog Shut Down Deasserted" 
--#ARGUMENTS  {} 
--#SEVERITY   INFORMATIONAL 

::= 1142658 
 
-- OS Watchdog Power Down Deasserted 
trapOSWatchdogPowerDownDeasserted TRAP-TYPE 
ENTERPRISE petevts 
DESCRIPTION 
 "OS Watchdog Power Down Deasserted" 

--#TYPE       "Watchdog Event" 
--#SUMMARY    "OS Watchdog Power Down Deasserted" 
--#ARGUMENTS  {} 
--#SEVERITY   INFORMATIONAL 

::= 1142659 
 
-- OS Watchdog Power Cycle Deasserted 
trapOSWatchdogPowerCycleDeasserted TRAP-TYPE 
ENTERPRISE petevts 
DESCRIPTION 
 "OS Watchdog Power Cycle Deasserted" 

--#TYPE       "Watchdog Event" 
--#SUMMARY    "OS Watchdog Power Cycle Deasserted" 
--#ARGUMENTS  {} 
--#SEVERITY   INFORMATIONAL 

::= 1142660 
 
-- OS Watchdog NMI / Diagnostic Interrupt Cleared 
trapOSWatchdogNMIOrDiagnosticInterruptCleared TRAP-TYPE 
ENTERPRISE petevts 
DESCRIPTION 
 "OS Watchdog NMI / Diagnostic Interrupt Cleared" 

--#TYPE       "Watchdog Event" 
--#SUMMARY    "OS Watchdog NMI / Diagnostic Interrupt Cleared" 
--#ARGUMENTS  {} 
--#SEVERITY   INFORMATIONAL 

::= 1142661 
 
-- OS Watchdog Expired, status only Event Cleared 
trapOSWatchdogExpiredEventCleared TRAP-TYPE 
ENTERPRISE petevts 
DESCRIPTION 
 "OS Watchdog Expired, status only Event Cleared" 

--#TYPE       "Watchdog Event" 
--#SUMMARY    "OS Watchdog Expired, status only Event Cleared" 
--#ARGUMENTS  {} 
--#SEVERITY   INFORMATIONAL 

::= 1142662 
 
-- OS Watchdog pre-timeout Interrupt, (non-NMI) Cleared 
trapOSWatchdogPreTimeoutInterruptCleared TRAP-TYPE 
ENTERPRISE petevts 
DESCRIPTION 
 "OS Watchdog pre-timeout Interrupt Cleared" 

--#TYPE       "Watchdog Event" 
--#SUMMARY    "OS Watchdog pre-timeout Interrupt Cleared" 
--#ARGUMENTS  {} 
--#SEVERITY   INFORMATIONAL 

::= 1142663 
 
 
-- ********************************************** 
-- *		System Event			* 
-- ********************************************** 

-- System Reconfigured 
trapSystemReconfigured TRAP-TYPE 
ENTERPRISE petevts 
DESCRIPTION 
 "System Reconfigured" 

--#TYPE       "System Event" 
--#SUMMARY    "System Reconfigured" 
--#ARGUMENTS  {} 
--#SEVERITY   INFORMATIONAL 

::= 1208064 
 
-- OEM System Boot Event 
trapOEMSystemBootEvent TRAP-TYPE 
ENTERPRISE petevts 
DESCRIPTION 
 "OEM System Boot Event" 

--#TYPE       "System Event" 
--#SUMMARY    "OEM System Boot Event" 
--#ARGUMENTS  {} 
--#SEVERITY   WARNING 

::= 1208065 
 
-- Undetermined system hardware failure 
trapUndeterminedSystemHardwareFailure TRAP-TYPE 
ENTERPRISE petevts 
DESCRIPTION 
 "Undetermined system hardware failure" 

--#TYPE       "System Event" 
--#SUMMARY    "Undetermined system hardware failure" 
--#ARGUMENTS  {} 
--#SEVERITY   CRITICAL 

::= 1208066 
 
-- SEL Entry added to Auxiliary Log 
trapEntryAddedToAuxiliaryLog TRAP-TYPE 
ENTERPRISE petevts 
DESCRIPTION 
 "SEL Entry added to Auxiliary Log" 

--#TYPE       "System Event" 
--#SUMMARY    "SEL Entry added to Auxiliary Log" 
--#ARGUMENTS  {} 
--#SEVERITY   INFORMATIONAL 

::= 1208067 
 
-- PEF Action 
trapPEFAction TRAP-TYPE 
ENTERPRISE petevts 
DESCRIPTION 
 "PEF Action is about to be taken. Event filters have been matched." 

--#TYPE       "System Event" 
--#SUMMARY    "PEF Action is about to be taken. Event filters have been matched." 
--#ARGUMENTS  {} 
--#SEVERITY   INFORMATIONAL 

::= 1208068 
 
-- Timestamp Clock Synch 
trapTimestampClockSynch TRAP-TYPE 
ENTERPRISE petevts 
DESCRIPTION 
 "Timestamp Clock Synch" 

--#TYPE       "System Event" 
--#SUMMARY    "Timestamp Clock Synch" 
--#ARGUMENTS  {} 
--#SEVERITY   INFORMATIONAL 

::= 1208069  

-- System Reconfigured Event Cleared 
trapSystemReconfiguredDeassert TRAP-TYPE 
ENTERPRISE petevts 
DESCRIPTION 
 "System Reconfigured Event Cleared" 

--#TYPE       "System Event" 
--#SUMMARY    "System Reconfigured Event Cleared" 
--#ARGUMENTS  {} 
--#SEVERITY   INFORMATIONAL 

::= 1208192 
 
-- OEM System Boot Event Cleared 
trapOEMSystemBootEventCleared TRAP-TYPE 
ENTERPRISE petevts 
DESCRIPTION 
 "OEM System Boot Event Cleared" 

--#TYPE       "System Event" 
--#SUMMARY    "OEM System Boot Event Cleared" 
--#ARGUMENTS  {} 
--#SEVERITY   INFORMATIONAL 

::= 1208193 
 
-- Undetermined system hardware failure Cleared 
trapUndeterminedSystemHardwareFailureCleared TRAP-TYPE 
ENTERPRISE petevts 
DESCRIPTION 
 "Undetermined system hardware failure Cleared" 

--#TYPE       "System Event" 
--#SUMMARY    "Undetermined system hardware failure Cleared" 
--#ARGUMENTS  {} 
--#SEVERITY   CRITICAL 

::= 1208194 
 
-- SEL Entry added to Auxiliary Log Deasserted 
trapEntryAddedToAuxiliaryLogDeassert TRAP-TYPE 
ENTERPRISE petevts 
DESCRIPTION 
 "SEL Entry added to Auxiliary Log Deasserted" 

--#TYPE       "System Event" 
--#SUMMARY    "SEL Entry added to Auxiliary Log Deasserted" 
--#ARGUMENTS  {} 
--#SEVERITY   INFORMATIONAL 

::= 1208195 
 
-- PEF Action Event Deasserted 
trapPEFActionEventDeassert TRAP-TYPE 
ENTERPRISE petevts 
DESCRIPTION 
 "PEF Action Event Deasserted" 

--#TYPE       "System Event" 
--#SUMMARY    "PEF Action Event Deasserted" 
--#ARGUMENTS  {} 
--#SEVERITY   INFORMATIONAL 

::= 1208196 
 
-- Timestamp Clock Synch Event Deasserted 
trapTimestampClockSynchEventDeassert TRAP-TYPE 
ENTERPRISE petevts 
DESCRIPTION 
 "Timestamp Clock Synch Event Deasserted" 

--#TYPE       "System Event" 
--#SUMMARY    "Timestamp Clock Synch Event Deasserted" 
--#ARGUMENTS  {} 
--#SEVERITY   INFORMATIONAL 

::= 1208197  
  
-- ********************************************** 
-- *		Critical Interrupt			* 
-- ********************************************** 

-- Front Panel NMI / Diagnostic Interrupt 
trapCriticalInterruptFrontPanelNMI TRAP-TYPE 
ENTERPRISE petevts 
DESCRIPTION  
 "Front Panel NMI / Diagnostic Interrupt" 

--#TYPE       "Critical Interrupts Event" 
--#SUMMARY    "Front Panel NMI / Diagnostic Interrupt" 
--#ARGUMENTS  {} 
--#SEVERITY   CRITICAL 

::= 1273600 
 
-- Critical Interrupt, Bus timeout error 
trapCriticalInterruptBusTimeout TRAP-TYPE 
ENTERPRISE petevts 
DESCRIPTION  
 "Critical Interrupt, Bus Timeout error" 

--#TYPE       "Critical Interrupts Event" 
--#SUMMARY    "Critical Interrupt, Bus Timeout error" 
--#ARGUMENTS  {} 
--#SEVERITY   CRITICAL 

::= 1273601 

-- Critical Interrupt, IO Channel Non-Maskable Interrupt 
trapCriticalInterruptIOChannelNMI TRAP-TYPE 
ENTERPRISE petevts 
DESCRIPTION  
 "Critical Interrupt, IO Channel check NMI error" 

--#TYPE       "Critical Interrupts Event" 
--#SUMMARY    "Critical Interrupt, IO Channel check NMI error" 
--#ARGUMENTS  {} 
--#SEVERITY   CRITICAL 

::= 1273602 
 
-- Critical Interrupt, Software Non-Maskable Interrupt error 
trapCriticalInterruptSoftwareNMI TRAP-TYPE 
ENTERPRISE petevts 
DESCRIPTION  
 "Critical Interrupt, software NMI error" 

--#TYPE       "Critical Interrupts Event" 
--#SUMMARY    "Critical Interrupt, software NMI error" 
--#ARGUMENTS  {} 
--#SEVERITY   CRITICAL 

::= 1273603 
 
-- Non special-cycle parity errors 
trapCriticalInterruptPCIPERR TRAP-TYPE 
ENTERPRISE petevts 
DESCRIPTION  
 "Critical Interrupt, PCI PERR parity error" 

--#TYPE       "Critical Interrupts Event" 
--#SUMMARY    "Critical Interrupt, PCI PERR parity error" 
--#ARGUMENTS  {} 
--#SEVERITY   CRITICAL 

::= 1273604 
 
-- Special-cycle parity errors 
trapCriticalInterruptPCISERR TRAP-TYPE 
ENTERPRISE petevts 
DESCRIPTION  
 "Critical Interrupt, PCI SERR parity error" 

--#TYPE       "Critical Interrupts Event" 
--#SUMMARY    "Critical Interrupt, PCI SERR parity error" 
--#ARGUMENTS  {} 
--#SEVERITY   CRITICAL 

::= 1273605 
 
-- EISA Fail Safe Timeout 
trapCriticalInterruptEISAFailSafeTimeout TRAP-TYPE 
ENTERPRISE petevts 
DESCRIPTION  
 "Critical Interrupt, EISA Fail Safe Timeout" 

--#TYPE       "Critical Interrupts Event" 
--#SUMMARY    "Critical Interrupt, EISA Fail Safe Timeout" 
--#ARGUMENTS  {} 
--#SEVERITY   CRITICAL 

::= 1273606 
 
-- Bus Correctable Error 
trapCriticalInterruptBusCorrectableError TRAP-TYPE 
ENTERPRISE petevts 
DESCRIPTION  
 "Critical Interrupt, Bus Correctable Error" 

--#TYPE       "Critical Interrupts Event" 
--#SUMMARY    "Critical Interrupt, Bus Correctable Error" 
--#ARGUMENTS  {} 
--#SEVERITY   CRITICAL 

::= 1273607 
 
-- Bus uncorrectable error 
trapCriticalInterruptBusUncorrect TRAP-TYPE 
ENTERPRISE petevts 
DESCRIPTION  
 "Critical Interrupt, Bus Uncorrectable error" 

--#TYPE       "Critical Interrupts Event" 
--#SUMMARY    "Critical Interrupt, Bus Uncorrectable error" 
--#ARGUMENTS  {} 
--#SEVERITY   CRITICAL 

::= 1273608 

-- Fatal non-maskable interrupt (NMI) 
trapCriticalInterruptFatalNMI TRAP-TYPE 
ENTERPRISE petevts 
DESCRIPTION  
 "Critical Interrupt, Fatal NMI error" 

--#TYPE       "Critical Interrupts Event" 
--#SUMMARY    "Critical Interrupt, Fatal NMI error" 
--#ARGUMENTS  {} 
--#SEVERITY   CRITICAL 

::= 1273609 
 
-- Bus Fatal Error 
trapCriticalInterruptFatalBusError TRAP-TYPE 
ENTERPRISE petevts 
DESCRIPTION  
 "Critical Interrupt, Bus Fatal Error" 

--#TYPE       "Critical Interrupts Event" 
--#SUMMARY    "Critical Interrupt, Bus Fatal Error" 
--#ARGUMENTS  {} 
--#SEVERITY   CRITICAL 

::= 1273610 
 
-- Bus Degraded (bus operating in a degraded performance state) 
trapCriticalInterruptBusDegraded TRAP-TYPE 
ENTERPRISE petevts 
DESCRIPTION  
 "Critical Interrupt, Bus Degraded (bus operating in a degraded performance state)" 

--#TYPE       "Critical Interrupts Event" 
--#SUMMARY    "Critical Interrupt, Bus Degraded (bus operating in a degraded performance state)" 
--#ARGUMENTS  {} 
--#SEVERITY   CRITICAL 

::= 1273611 
 
-- Front Panel NMI / Diagnostic Interrupt Cleared 
trapCriticalInterruptFrontPanelNMICleared TRAP-TYPE 
ENTERPRISE petevts 
DESCRIPTION  
 "Front Panel NMI / Diagnostic Interrupt Cleared" 

--#TYPE       "Critical Interrupts Event" 
--#SUMMARY    "Front Panel NMI / Diagnostic Interrupt Cleared" 
--#ARGUMENTS  {} 
--#SEVERITY   INFORMATIONAL 

::= 1273728 
 
-- Critical Interrupt, Bus timeout error Cleared 
trapCriticalInterruptBusTimeoutCleared TRAP-TYPE 
ENTERPRISE petevts 
DESCRIPTION  
 "Critical Interrupt, Bus Timeout error Cleared"  

--#TYPE       "Critical Interrupts Event" 
--#SUMMARY    "Critical Interrupt, Bus Timeout error Cleared" 
--#ARGUMENTS  {} 
--#SEVERITY   INFORMATIONAL 

::= 1273729 

-- Critical Interrupt, IO Channel Non-Maskable Interrupt Cleared 
trapCriticalInterruptIOChannelNMICleared TRAP-TYPE 
ENTERPRISE petevts 
DESCRIPTION  
 "Critical Interrupt, IO Channel check NMI error Cleared" 

--#TYPE       "Critical Interrupts Event" 
--#SUMMARY    "Critical Interrupt, IO Channel check NMI error Cleared" 
--#ARGUMENTS  {} 
--#SEVERITY   INFORMATIONAL 

::= 1273730 
 
-- Critical Interrupt, Software Non-Maskable Interrupt error Cleared 
trapCriticalInterruptSoftwareNMICleared TRAP-TYPE 
ENTERPRISE petevts 
DESCRIPTION  
 "Critical Interrupt, software NMI error Cleared" 

--#TYPE       "Critical Interrupts Event" 
--#SUMMARY    "Critical Interrupt, software NMI error Cleared" 
--#ARGUMENTS  {} 
--#SEVERITY   INFORMATIONAL 

::= 1273731 
 
-- Non special-cycle parity errors Cleared 
trapCriticalInterruptPCIPERRCleared TRAP-TYPE 
ENTERPRISE petevts 
DESCRIPTION  
 "Critical Interrupt, PCI PERR parity error Cleared" 

--#TYPE       "Critical Interrupts Event" 
--#SUMMARY    "Critical Interrupt, PCI PERR parity error Cleared" 
--#ARGUMENTS  {} 
--#SEVERITY   INFORMATIONAL 

::= 1273732 
 
-- Special-cycle parity errors Cleared 
trapCriticalInterruptPCISERRCleared TRAP-TYPE 
ENTERPRISE petevts 
DESCRIPTION  
 "Critical Interrupt, PCI SERR parity error Cleared" 

--#TYPE       "Critical Interrupts Event" 
--#SUMMARY    "Critical Interrupt, PCI SERR parity error Cleared" 
--#ARGUMENTS  {} 
--#SEVERITY   INFORMATIONAL 

::= 1273733 
  
-- EISA Fail Safe Timeout Event Cleared 
trapCriticalInterruptEISAFailSafeTimeoutCleared TRAP-TYPE 
ENTERPRISE petevts 
DESCRIPTION  
 "Critical Interrupt, EISA Fail Safe Timeout Event Cleared" 

--#TYPE       "Critical Interrupts Event" 
--#SUMMARY    "Critical Interrupt, EISA Fail Safe Timeout Event Cleared" 
--#ARGUMENTS  {} 
--#SEVERITY   INFORMATIONAL 

::= 1273734 
 
-- Bus Correctable Error Cleared 
trapCriticalInterruptBusCorrectableErrorCleared TRAP-TYPE 
ENTERPRISE petevts 
DESCRIPTION  
 "Critical Interrupt, Bus Correctable Error Cleared" 

--#TYPE       "Critical Interrupts Event" 
--#SUMMARY    "Critical Interrupt, Bus Correctable Error Cleared" 
--#ARGUMENTS  {} 
--#SEVERITY   INFORMATIONAL 

::= 1273735 
 
-- Bus uncorrectable error Cleared 
trapCriticalInterruptBusUncorrectCleared TRAP-TYPE 
ENTERPRISE petevts 
DESCRIPTION  
 "Critical Interrupt, Bus Uncorrectable error Cleared" 

--#TYPE       "Critical Interrupts Event" 
--#SUMMARY    "Critical Interrupt, Bus Uncorrectable error Cleared" 
--#ARGUMENTS  {} 
--#SEVERITY   INFORMATIONAL 

::= 1273736 

-- Fatal non-maskable interrupt (NMI) Cleared 
trapCriticalInterruptFatalNMICleared TRAP-TYPE 
ENTERPRISE petevts 
DESCRIPTION  
 "Critical Interrupt, Fatal NMI error Cleared" 

--#TYPE       "Critical Interrupts Event" 
--#SUMMARY    "Critical Interrupt, Fatal NMI error Cleared" 
--#ARGUMENTS  {} 
--#SEVERITY   INFORMATIONAL 

::= 1273737 
 
-- Bus Fatal Error Cleared 
trapCriticalInterruptFatalBusErrorCleared TRAP-TYPE 
ENTERPRISE petevts 
DESCRIPTION  
 "Critical Interrupt, Bus Fatal Error Cleared" 

--#TYPE       "Critical Interrupts Event" 
--#SUMMARY    "Critical Interrupt, Bus Fatal Error Cleared" 
--#ARGUMENTS  {} 
--#SEVERITY   INFORMATIONAL 

::= 1273738 
 
-- Bus Degraded (bus operating in a degraded performance state) Event Cleared 
trapCriticalInterruptBusDegradedEventCleared TRAP-TYPE 
ENTERPRISE petevts 
DESCRIPTION  
 "Critical Interrupt, Bus Degraded (bus operating in a degraded performance state) Event Cleared"  

--#TYPE       "Critical Interrupts Event" 
--#SUMMARY    "Critical Interrupt, Bus Degraded (bus operating in a degraded performance state) Event Cleared" 
--#ARGUMENTS  {} 
--#SEVERITY   INFORMATIONAL 

::= 1273739 
 
-- ********************************************** 
-- *		Button/Switch			* 
-- ********************************************** 

-- Power Button pressed 
trapPowerButtonPressed TRAP-TYPE 
ENTERPRISE petevts 
DESCRIPTION 
 "Power Button pressed." 

--#TYPE       "Button/Switch Event" 
--#SUMMARY    "Power Button pressed." 
--#ARGUMENTS  {} 
--#SEVERITY   INFORMATIONAL 

::= 1339136 

-- Sleep Button pressed 
trapSleepButtonPressed TRAP-TYPE 
ENTERPRISE petevts 
DESCRIPTION 
 "Sleep Button pressed." 

--#TYPE       "Button/Switch Event" 
--#SUMMARY    "Sleep Button pressed." 
--#ARGUMENTS  {} 
--#SEVERITY   INFORMATIONAL 

::= 1339137 
 
-- Reset Button pressed 
trapResetButtonPressed TRAP-TYPE 
ENTERPRISE petevts 
DESCRIPTION 
 "Reset Button pressed." 

--#TYPE       "Button/Switch Event" 
--#SUMMARY    "Reset Button pressed." 
--#ARGUMENTS  {} 
--#SEVERITY   INFORMATIONAL 

::= 1339138 
 
-- FRU latch open 
trapFRULatchOpen TRAP-TYPE 
ENTERPRISE petevts 
DESCRIPTION 
 "FRU latch open (Switch indicating FRU latch is in unlatched position and FRU is mechanically removable)" 

--#TYPE       "Button/Switch Event" 
--#SUMMARY    "FRU latch open" 
--#ARGUMENTS  {} 
--#SEVERITY   INFORMATIONAL 

::= 1339139 
 
-- FRU service request button 
trapFRUServiceRequestButton TRAP-TYPE 
ENTERPRISE petevts 
DESCRIPTION 
 "FRU service request button" 

--#TYPE       "Button/Switch Event" 
--#SUMMARY    "FRU service request button" 
--#ARGUMENTS  {} 
--#SEVERITY   INFORMATIONAL 

::= 1339140 
 
-- Power Button Released 
trapPowerButtonReleased TRAP-TYPE 
ENTERPRISE petevts 
DESCRIPTION 
 "Power Button Released." 

--#TYPE       "Button/Switch Event" 
--#SUMMARY    "Power Button Released." 
--#ARGUMENTS  {} 
--#SEVERITY   INFORMATIONAL 

::= 1339264 

-- Sleep Button Released 
trapSleepButtonReleased TRAP-TYPE 
ENTERPRISE petevts 
DESCRIPTION 
 "Sleep Button Released." 

--#TYPE       "Button/Switch Event" 
--#SUMMARY    "Sleep Button Released." 
--#ARGUMENTS  {} 
--#SEVERITY   INFORMATIONAL 

::= 1339265 
 
-- Reset Button Released 
trapResetButtonReleased TRAP-TYPE 
ENTERPRISE petevts 
DESCRIPTION 
 "Reset Button Released." 

--#TYPE       "Button/Switch Event" 
--#SUMMARY    "Reset Button Released." 
--#ARGUMENTS  {} 
--#SEVERITY   INFORMATIONAL 

::= 1339266 
 
-- FRU latch Closed 
trapFRULatchClosed TRAP-TYPE 
ENTERPRISE petevts 
DESCRIPTION 
 "FRU latch Closed (Switch indicating FRU latch is in latched position)" 

--#TYPE       "Button/Switch Event" 
--#SUMMARY    "FRU latch Closed" 
--#ARGUMENTS  {} 
--#SEVERITY   INFORMATIONAL 

::= 1339267 
 
-- FRU service request button Released 
trapFRUServiceRequestButtonReleased TRAP-TYPE 
ENTERPRISE petevts 
DESCRIPTION 
 "FRU service request button Released" 

--#TYPE       "Button/Switch Event" 
--#SUMMARY    "FRU service request button Released" 
--#ARGUMENTS  {} 
--#SEVERITY   INFORMATIONAL 

::= 1339268 
 
-- ********************************************** 
-- *		Module/Board			* 
-- ********************************************** 
-- Module/Board State Deasserted 
trapBoardStateDeasserted TRAP-TYPE 
ENTERPRISE petevts 
DESCRIPTION 
 "Module/Board State Deasserted" 

--#TYPE       "Module/Board Event" 
--#SUMMARY    "Module/Board State Deasserted" 
--#ARGUMENTS  {} 
--#SEVERITY   INFORMATIONAL 

::= 1377024 

-- Module/Board State Asserted 
trapBoardStateAsserted TRAP-TYPE 
ENTERPRISE petevts 
DESCRIPTION 
 "Module/Board State Asserted" 

--#TYPE       "Module/Board Event" 
--#SUMMARY    "Module/Board State Asserted" 
--#ARGUMENTS  {} 
--#SEVERITY   INFORMATIONAL 

::= 1377025 
 
-- Module/Board Predictive Failure Deasserted 
trapBoardPredictiveFailureDeasserted TRAP-TYPE 
ENTERPRISE petevts 
DESCRIPTION 
 "Module/Board Predictive Failure Deasserted" 

--#TYPE       "Module/Board Event" 
--#SUMMARY    "Module/Board Predictive Failure Deasserted" 
--#ARGUMENTS  {} 
--#SEVERITY   INFORMATIONAL 

::= 1377280 
 
-- Module/Board Predictive Failure Asserted 
trapBoardPredictiveFailureAsserted TRAP-TYPE 
ENTERPRISE petevts 
DESCRIPTION 
 "Module/Board Predictive Failure Asserted" 

--#TYPE       "Module/Board Event" 
--#SUMMARY    "Module/Board Predictive Failure Asserted" 
--#ARGUMENTS  {} 
--#SEVERITY   INFORMATIONAL 

::= 1377281 
 
-- ********************************************** 
-- *		Microcontroller/Coprocessor			* 
-- ********************************************** 
-- Microcontroller/Coprocessor State Deasserted 
trapMicrocontrollerStateDeasserted TRAP-TYPE 
ENTERPRISE petevts 
DESCRIPTION 
 "Microcontroller/Coprocessor State Deasserted" 

--#TYPE       "Microcontroller/Coprocessor Event" 
--#SUMMARY    "Microcontroller/Coprocessor State Deasserted" 
--#ARGUMENTS  {} 
--#SEVERITY   INFORMATIONAL 

::= 1442560 

-- Microcontroller/Coprocessor State Asserted 
trapMicrocontrollerStateAsserted TRAP-TYPE 
ENTERPRISE petevts 
DESCRIPTION 
 "Microcontroller/Coprocessor State Asserted" 

--#TYPE       "Microcontroller/Coprocessor Event" 
--#SUMMARY    "Microcontroller/Coprocessor State Asserted" 
--#ARGUMENTS  {} 
--#SEVERITY   INFORMATIONAL 

::= 1442561 
 
-- Microcontroller/Coprocessor Predictive Failure Deasserted 
trapMicrocontrollerPredictiveFailureDeasserted TRAP-TYPE 
ENTERPRISE petevts 
DESCRIPTION 
 "Microcontroller/Coprocessor Predictive Failure Deasserted" 

--#TYPE       "Microcontroller/Coprocessor Event" 
--#SUMMARY    "Microcontroller/Coprocessor Predictive Failure Deasserted" 
--#ARGUMENTS  {} 
--#SEVERITY   INFORMATIONAL 

::= 1442816 
 
-- Microcontroller/Coprocessor Predictive Failure Asserted 
trapMicrocontrollerPredictiveFailureAsserted TRAP-TYPE 
ENTERPRISE petevts 
DESCRIPTION 
 "Microcontroller/Coprocessor Predictive Failure Asserted" 

--#TYPE       "Microcontroller/Coprocessor Event" 
--#SUMMARY    "Microcontroller/Coprocessor Predictive Failure Asserted" 
--#ARGUMENTS  {} 
--#SEVERITY   INFORMATIONAL 

::= 1442817 
 
-- ********************************************** 
-- *		Add-in Card			* 
-- ********************************************** 
-- Add-in Card State Deasserted 
trapAddInCardStateDeasserted TRAP-TYPE 
ENTERPRISE petevts 
DESCRIPTION 
 "Add-in Card State Deasserted" 

--#TYPE       "Add-in Card Event" 
--#SUMMARY    "Add-in Card State Deasserted" 
--#ARGUMENTS  {} 
--#SEVERITY   INFORMATIONAL 

::= 1508096 

-- Add-in Card State Asserted 
trapAddInCardStateAsserted TRAP-TYPE 
ENTERPRISE petevts 
DESCRIPTION 
 "Add-in Card State Asserted" 

--#TYPE       "Add-in Card Event" 
--#SUMMARY    "Add-in Card State Asserted" 
--#ARGUMENTS  {} 
--#SEVERITY   INFORMATIONAL 

::= 1508097 
 
-- Add-in Card Predictive Failure Deasserted 
trapAddInCardPredictiveFailureDeasserted TRAP-TYPE 
ENTERPRISE petevts 
DESCRIPTION 
 "Add-in Card Predictive Failure Deasserted" 

--#TYPE       "Add-in Card Event" 
--#SUMMARY    "Add-in Card Predictive Failure Deasserted" 
--#ARGUMENTS  {} 
--#SEVERITY   INFORMATIONAL 

::= 1508352 
 
-- Add-in Card Predictive Failure Asserted 
trapAddInCardPredictiveFailureAsserted TRAP-TYPE 
ENTERPRISE petevts 
DESCRIPTION 
 "Add-in Card Predictive Failure Asserted" 

--#TYPE       "Add-in Card Event" 
--#SUMMARY    "Add-in Card Predictive Failure Asserted" 
--#ARGUMENTS  {} 
--#SEVERITY   INFORMATIONAL 

::= 1508353 

-- ********************************************** 
-- *		Chassis			* 
-- ********************************************** 
-- Chassis State Deasserted 
trapChassisStateDeasserted TRAP-TYPE 
ENTERPRISE petevts 
DESCRIPTION 
 "Chassis State Deasserted" 

--#TYPE       "Chassis Event" 
--#SUMMARY    "Chassis State Deasserted" 
--#ARGUMENTS  {} 
--#SEVERITY   INFORMATIONAL 

::= 1573632 

-- Chassis State Asserted 
trapChassisStateAsserted TRAP-TYPE 
ENTERPRISE petevts 
DESCRIPTION 
 "Chassis State Asserted" 

--#TYPE       "Chassis Event" 
--#SUMMARY    "Chassis State Asserted" 
--#ARGUMENTS  {} 
--#SEVERITY   INFORMATIONAL 

::= 1573633 
 
-- Chassis Predictive Failure Deasserted 
trapChassisPredictiveFailureDeasserted TRAP-TYPE 
ENTERPRISE petevts 
DESCRIPTION 
 "Chassis Predictive Failure Deasserted" 

--#TYPE       "Chassis Event" 
--#SUMMARY    "Chassis Predictive Failure Deasserted" 
--#ARGUMENTS  {} 
--#SEVERITY   INFORMATIONAL 

::= 1573888 
 
-- Chassis Predictive Failure Asserted 
trapChassisPredictiveFailureAsserted TRAP-TYPE 
ENTERPRISE petevts 
DESCRIPTION 
 "Chassis Predictive Failure Asserted" 

--#TYPE       "Chassis Event" 
--#SUMMARY    "Chassis Predictive Failure Asserted" 
--#ARGUMENTS  {} 
--#SEVERITY   INFORMATIONAL 

::= 1573889 

-- ********************************************** 
-- *		Chip Set			* 
-- ********************************************** 
-- Chip Set State Deasserted 
trapChipSetStateDeasserted TRAP-TYPE 
ENTERPRISE petevts 
DESCRIPTION 
 "Chip Set State Deasserted" 

--#TYPE       "Chip Set Event" 
--#SUMMARY    "Chip Set State Deasserted" 
--#ARGUMENTS  {} 
--#SEVERITY   INFORMATIONAL 

::= 1639168 

-- Chip Set State Asserted 
trapChipSetStateAsserted TRAP-TYPE 
ENTERPRISE petevts 
DESCRIPTION 
 "Chip Set State Asserted" 

--#TYPE       "Chip Set Event" 
--#SUMMARY    "Chip Set State Asserted" 
--#ARGUMENTS  {} 
--#SEVERITY   INFORMATIONAL 

::= 1639169 
 
-- Chip Set Predictive Failure Deasserted 
trapChipSetPredictiveFailureDeasserted TRAP-TYPE 
ENTERPRISE petevts 
DESCRIPTION 
 "Chip Set Predictive Failure Deasserted" 

--#TYPE       "Chip Set Event" 
--#SUMMARY    "Chip Set Predictive Failure Deasserted" 
--#ARGUMENTS  {} 
--#SEVERITY   INFORMATIONAL 

::= 1639424 
 
-- Chip Set Predictive Failure Asserted 
trapChipSetPredictiveFailureAsserted TRAP-TYPE 
ENTERPRISE petevts 
DESCRIPTION 
 "Chip Set Predictive Failure Asserted" 

--#TYPE       "Chip Set Event" 
--#SUMMARY    "Chip Set Predictive Failure Asserted" 
--#ARGUMENTS  {} 
--#SEVERITY   INFORMATIONAL 

::= 1639425 
 
-- Soft Power Control Failure 
trapSoftPowerControlFailure TRAP-TYPE 
ENTERPRISE petevts 
DESCRIPTION 
 "Chip Set did not respond to BMC request to change system power state." 

--#TYPE       "Chip Set Event" 
--#SUMMARY    "Soft Power Control Failure" 
--#ARGUMENTS  {} 
--#SEVERITY   WARNING 

::= 1666816 

-- Thermal Trip Occured 
trapThermalTrip TRAP-TYPE 
ENTERPRISE petevts 
DESCRIPTION 
 "Thermal Trip Occured" 

--#TYPE       "Chip Set Event" 
--#SUMMARY    "Thermal Trip Occured" 
--#ARGUMENTS  {} 
--#SEVERITY   WARNING 

::= 1666817 
 
-- Soft Power Control Failure Cleared 
trapSoftPowerControlFailureCleared TRAP-TYPE 
ENTERPRISE petevts 
DESCRIPTION 
 "Chip Set started responding to BMC request to change system power state." 

--#TYPE       "Chip Set Event" 
--#SUMMARY    "Soft Power Control Failure Cleared" 
--#ARGUMENTS  {} 
--#SEVERITY   INFORMATIONAL 

::= 1666944 

-- Thermal Trip Cleared 
trapThermalTripCleared TRAP-TYPE 
ENTERPRISE petevts 
DESCRIPTION 
 "Thermal Trip Cleared" 

--#TYPE       "Chip Set Event" 
--#SUMMARY    "Thermal Trip Cleared" 
--#ARGUMENTS  {} 
--#SEVERITY   INFORMATIONAL 

::= 1666945 
 
-- ********************************************** 
-- *		Other FRU			* 
-- ********************************************** 
-- FRU State Deasserted 
trapFRUStateDeasserted TRAP-TYPE 
ENTERPRISE petevts 
DESCRIPTION 
 "FRU State Deasserted" 

--#TYPE       "Other FRU Event" 
--#SUMMARY    "FRU State Deasserted" 
--#ARGUMENTS  {} 
--#SEVERITY   INFORMATIONAL 

::= 1704704 

-- FRU State Asserted 
trapFRUStateAsserted TRAP-TYPE 
ENTERPRISE petevts 
DESCRIPTION 
 "FRU State Asserted" 

--#TYPE       "Other FRU Event" 
--#SUMMARY    "FRU State Asserted" 
--#ARGUMENTS  {} 
--#SEVERITY   INFORMATIONAL 

::= 1704705 
 
-- FRU Predictive Failure Deasserted 
trapFRUPredictiveFailureDeasserted TRAP-TYPE 
ENTERPRISE petevts 
DESCRIPTION 
 "FRU Predictive Failure Deasserted" 

--#TYPE       "Other FRU Event" 
--#SUMMARY    "FRU Predictive Failure Deasserted" 
--#ARGUMENTS  {} 
--#SEVERITY   INFORMATIONAL 

::= 1704960 
 
-- FRU Predictive Failure Asserted 
trapFRUPredictiveFailureAsserted TRAP-TYPE 
ENTERPRISE petevts 
DESCRIPTION 
 "FRU Predictive Failure Asserted" 

--#TYPE       "Other FRU Event" 
--#SUMMARY    "FRU Predictive Failure Asserted" 
--#ARGUMENTS  {} 
--#SEVERITY   INFORMATIONAL 

::= 1704961 

-- ********************************************** 
-- *		Cable / Interconnect			* 
-- ********************************************** 
-- Cable / Interconnect State Deasserted 
trapCableStateDeasserted TRAP-TYPE 
ENTERPRISE petevts 
DESCRIPTION 
 "Cable / Interconnect State Deasserted" 

--#TYPE       "Other Cable / Interconnect Event" 
--#SUMMARY    "Cable / Interconnect State Deasserted" 
--#ARGUMENTS  {} 
--#SEVERITY   INFORMATIONAL 

::= 1770240 

-- Cable / Interconnect State Asserted 
trapCableStateAsserted TRAP-TYPE 
ENTERPRISE petevts 
DESCRIPTION 
 "Cable / Interconnect State Asserted" 

--#TYPE       "Other Cable / Interconnect Event" 
--#SUMMARY    "Cable / Interconnect State Asserted" 
--#ARGUMENTS  {} 
--#SEVERITY   INFORMATIONAL 

::= 1770241 
 
-- Cable / Interconnect Predictive Failure Deasserted 
trapCablePredictiveFailureDeasserted TRAP-TYPE 
ENTERPRISE petevts 
DESCRIPTION 
 "Cable / Interconnect Predictive Failure Deasserted" 

--#TYPE       "Other Cable / Interconnect Event" 
--#SUMMARY    "Cable / Interconnect Predictive Failure Deasserted" 
--#ARGUMENTS  {} 
--#SEVERITY   INFORMATIONAL 

::= 1770496 
 
-- Cable / Interconnect Predictive Failure Asserted 
trapCablePredictiveFailureAsserted TRAP-TYPE 
ENTERPRISE petevts 
DESCRIPTION 
 "Cable / Interconnect Predictive Failure Asserted" 

--#TYPE       "Other Cable / Interconnect Event" 
--#SUMMARY    "Cable / Interconnect Predictive Failure Asserted" 
--#ARGUMENTS  {} 
--#SEVERITY   INFORMATIONAL 

::= 1770497 

-- Cable/Interconnect is connected 
trapCableConnected TRAP-TYPE 
ENTERPRISE petevts 
DESCRIPTION 
 "Cable/Interconnect is connected" 

--#TYPE       "Other Cable / Interconnect Event" 
--#SUMMARY    "Cable/Interconnect is connected" 
--#ARGUMENTS  {} 
--#SEVERITY   INFORMATIONAL 

::= 1797888 

-- Configuration Error 
trapConfigurationError TRAP-TYPE 
ENTERPRISE petevts 
DESCRIPTION 
 "Configuration Error - Incorrect cable connected / Incorrect interconnection" 

--#TYPE       "Other Cable / Interconnect Event" 
--#SUMMARY    "Configuration Error" 
--#ARGUMENTS  {} 
--#SEVERITY   INFORMATIONAL 

::= 1797889 
 
-- Cable/Interconnect is disconnected 
trapCableDisConnected TRAP-TYPE 
ENTERPRISE petevts 
DESCRIPTION 
 "Cable/Interconnect is disconnected" 

--#TYPE       "Other Cable / Interconnect Event" 
--#SUMMARY    "Cable/Interconnect is disconnected" 
--#ARGUMENTS  {} 
--#SEVERITY   WARNING 

::= 1798016 

-- Configuration Error Cleared 
trapConfigurationErrorCleared TRAP-TYPE 
ENTERPRISE petevts 
DESCRIPTION 
 "Configuration Error Cleared" 

--#TYPE       "Other Cable / Interconnect Event" 
--#SUMMARY    "Configuration Error Cleared" 
--#ARGUMENTS  {} 
--#SEVERITY   INFORMATIONAL 

::= 1798017 
 
-- ********************************************** 
-- *		Terminator			* 
-- ********************************************** 
-- Terminator State Deasserted 
trapTerminatorStateDeasserted TRAP-TYPE 
ENTERPRISE petevts 
DESCRIPTION 
 "Terminator State Deasserted" 

--#TYPE       "Terminator Event" 
--#SUMMARY    "Terminator State Deasserted" 
--#ARGUMENTS  {} 
--#SEVERITY   INFORMATIONAL 

::= 1835776 

-- Terminator State Asserted 
trapTerminatorStateAsserted TRAP-TYPE 
ENTERPRISE petevts 
DESCRIPTION 
 "Terminator State Asserted" 

--#TYPE       "Terminator Event" 
--#SUMMARY    "Terminator State Asserted" 
--#ARGUMENTS  {} 
--#SEVERITY   INFORMATIONAL 

::= 1835777 
 
-- Terminator Predictive Failure Deasserted 
trapTerminatorPredictiveFailureDeasserted TRAP-TYPE 
ENTERPRISE petevts 
DESCRIPTION 
 "Terminator Predictive Failure Deasserted" 

--#TYPE       "Terminator Event" 
--#SUMMARY    "Terminator Predictive Failure Deasserted" 
--#ARGUMENTS  {} 
--#SEVERITY   INFORMATIONAL 

::= 1836032 
 
-- Terminator Predictive Failure Asserted 
trapTerminatorPredictiveFailureAsserted TRAP-TYPE 
ENTERPRISE petevts 
DESCRIPTION 
 "Terminator Predictive Failure Asserted" 

--#TYPE       "Terminator Event" 
--#SUMMARY    "Terminator Predictive Failure Asserted" 
--#ARGUMENTS  {} 
--#SEVERITY   INFORMATIONAL 

::= 1836033 
 
-- ********************************************** 
-- *		System Boot / Restart Initiated		* 
-- ********************************************** 

-- System Boot / Restart Initiated by power up 
trapSystemBootByPowerUp TRAP-TYPE 
ENTERPRISE petevts 
DESCRIPTION 
 "System Boot / Restart Initiated by power up" 

--#TYPE       "System Boot / Restart Event" 
--#SUMMARY    "System Boot / Restart Initiated by power up" 
--#ARGUMENTS  {} 
--#SEVERITY   INFORMATIONAL 

::= 1928960 
 
-- System Boot / Restart Initiated by Hard Reset 
trapSystemBootByHardReset TRAP-TYPE 
ENTERPRISE petevts 
DESCRIPTION 
 "System Boot / Restart Initiated by Hard Reset" 

--#TYPE       "System Boot / Restart Event" 
--#SUMMARY    "System Boot / Restart Initiated by Hard Reset" 
--#ARGUMENTS  {} 
--#SEVERITY   INFORMATIONAL 

::= 1928961 
 
-- System Boot / Restart Initiated by Warm Reset 
trapSystemBootByWarmReset TRAP-TYPE 
ENTERPRISE petevts 
DESCRIPTION 
 "System Boot / Restart Initiated by Warm Reset" 

--#TYPE       "System Boot / Restart Event" 
--#SUMMARY    "System Boot / Restart Initiated by Warm Reset" 
--#ARGUMENTS  {} 
--#SEVERITY   INFORMATIONAL 

::= 1928962 
 
-- System Boot / Restart - User requested PXE boot 
trapUserRequestedPXEBoot TRAP-TYPE 
ENTERPRISE petevts 
DESCRIPTION 
 "System Boot / Restart - User requested PXE boot" 

--#TYPE       "System Boot / Restart Event" 
--#SUMMARY    "System Boot / Restart - User requested PXE boot" 
--#ARGUMENTS  {} 
--#SEVERITY   INFORMATIONAL 

::= 1928963 
 
-- System Boot / Restart - Automatic boot to diagnostic 
trapAutomaticDiagnosticBoot TRAP-TYPE 
ENTERPRISE petevts 
DESCRIPTION 
 "System Boot / Restart - Automatic boot to diagnostic" 

--#TYPE       "System Boot / Restart Event" 
--#SUMMARY    "System Boot / Restart - Automatic boot to diagnostic" 
--#ARGUMENTS  {} 
--#SEVERITY   INFORMATIONAL 

::= 1928964 

-- System Boot / Restart - OS / run-time software initiated hard reset 
trapOSInitiatedHardReset TRAP-TYPE 
ENTERPRISE petevts 
DESCRIPTION 
 "System Boot / Restart - OS / run-time software initiated hard reset" 

--#TYPE       "System Boot / Restart Event" 
--#SUMMARY    "System Boot / Restart - OS / run-time software initiated hard reset" 
--#ARGUMENTS  {} 
--#SEVERITY   INFORMATIONAL 

::= 1928965 
 
-- System Boot / Restart - OS / run-time software initiated Warm reset 
trapOSInitiatedWarmReset TRAP-TYPE 
ENTERPRISE petevts 
DESCRIPTION 
 "System Boot / Restart - OS / run-time software initiated Warm reset" 

--#TYPE       "System Boot / Restart Event" 
--#SUMMARY    "System Boot / Restart - OS / run-time software initiated Warm reset" 
--#ARGUMENTS  {} 
--#SEVERITY   INFORMATIONAL 

::= 1928966 
 
-- System Boot / Restart - System Restart 
trapSystemRestart TRAP-TYPE 
ENTERPRISE petevts 
DESCRIPTION 
 "System Boot / Restart - Restart cause per Get System Restart Cause command" 

--#TYPE       "System Boot / Restart Event" 
--#SUMMARY    "System Boot / Restart - Restart cause per Get System Restart Cause command" 
--#ARGUMENTS  {} 
--#SEVERITY   INFORMATIONAL 

::= 1928967 

-- System Boot / Restart Initiated by power up Deasserted 
trapSystemBootByPowerUpDeasserted TRAP-TYPE 
ENTERPRISE petevts 
DESCRIPTION 
 "System Boot / Restart Initiated by power up Deasserted" 

--#TYPE       "System Boot / Restart Event" 
--#SUMMARY    "System Boot / Restart Initiated by power up Deasserted" 
--#ARGUMENTS  {} 
--#SEVERITY   INFORMATIONAL 

::= 1929088 
 
-- System Boot / Restart Initiated by Hard Reset Deasserted 
trapSystemBootByHardResetDeasserted TRAP-TYPE 
ENTERPRISE petevts 
DESCRIPTION 
 "System Boot / Restart Initiated by Hard Reset Deasserted" 

--#TYPE       "System Boot / Restart Event" 
--#SUMMARY    "System Boot / Restart Initiated by Hard Reset Deasserted" 
--#ARGUMENTS  {} 
--#SEVERITY   INFORMATIONAL 

::= 1929089 
 
-- System Boot / Restart Initiated by Warm Reset Deasserted 
trapSystemBootByWarmResetDeasserted TRAP-TYPE 
ENTERPRISE petevts 
DESCRIPTION 
 "System Boot / Restart Initiated by Warm Reset Deasserted" 

--#TYPE       "System Boot / Restart Event" 
--#SUMMARY    "System Boot / Restart Initiated by Warm Reset Deasserted" 
--#ARGUMENTS  {} 
--#SEVERITY   INFORMATIONAL 

::= 1929090 
 
-- System Boot / Restart - User requested PXE boot Deasserted 
trapUserRequestedPXEBootDeasserted TRAP-TYPE 
ENTERPRISE petevts 
DESCRIPTION 
 "System Boot / Restart - User requested PXE boot Deasserted" 

--#TYPE       "System Boot / Restart Event" 
--#SUMMARY    "System Boot / Restart - User requested PXE boot Deasserted" 
--#ARGUMENTS  {} 
--#SEVERITY   INFORMATIONAL 

::= 1929091 
 
-- System Boot / Restart - Automatic boot to diagnostic Deasserted 
trapAutomaticDiagnosticBootDeasserted TRAP-TYPE 
ENTERPRISE petevts 
DESCRIPTION 
 "System Boot / Restart - Automatic boot to diagnostic Deasserted" 

--#TYPE       "System Boot / Restart Event" 
--#SUMMARY    "System Boot / Restart - Automatic boot to diagnostic Deasserted" 
--#ARGUMENTS  {} 
--#SEVERITY   INFORMATIONAL 

::= 1929092 

-- System Boot / Restart - OS / run-time software initiated hard reset Deasserted 
trapOSInitiatedHardResetDeasserted TRAP-TYPE 
ENTERPRISE petevts 
DESCRIPTION 
 "System Boot / Restart - OS / run-time software initiated hard reset Deasserted" 

--#TYPE       "System Boot / Restart Event" 
--#SUMMARY    "System Boot / Restart - OS / run-time software initiated hard reset Deasserted" 
--#ARGUMENTS  {} 
--#SEVERITY   INFORMATIONAL 

::= 1929093 
 
-- System Boot / Restart - OS / run-time software initiated Warm reset Deasserted 
trapOSInitiatedWarmResetDeasserted TRAP-TYPE 
ENTERPRISE petevts 
DESCRIPTION 
 "System Boot / Restart - OS / run-time software initiated Warm reset Deasserted" 

--#TYPE       "System Boot / Restart Event" 
--#SUMMARY    "System Boot / Restart - OS / run-time software initiated Warm reset Deasserted" 
--#ARGUMENTS  {} 
--#SEVERITY   INFORMATIONAL 

::= 1929094 
 
-- System Boot / Restart - System Restart Deasserted 
trapSystemRestartDeasserted TRAP-TYPE 
ENTERPRISE petevts 
DESCRIPTION 
 "System Boot / Restart - Restart cause per Get System Restart Cause command Deasserted" 

--#TYPE       "System Boot / Restart Event" 
--#SUMMARY    "System Boot / Restart - Restart cause per Get System Restart Cause command Deasserted" 
--#ARGUMENTS  {} 
--#SEVERITY   INFORMATIONAL 

::= 1929095 
 
-- ********************************************** 
-- *		Boot Error			* 
-- ********************************************** 

-- Boot Error - No bootable media 
trapNoBootableMedia TRAP-TYPE 
ENTERPRISE petevts 
DESCRIPTION 
 "Boot Error - No bootable media" 

--#TYPE       "Boot Error Event" 
--#SUMMARY    "Boot Error - No bootable media" 
--#ARGUMENTS  {} 
--#SEVERITY   CRITICAL 

::= 1994496 

-- Boot Error - Non-bootable diskette left in drive 
trapNonBootableDisketteInDrive TRAP-TYPE 
ENTERPRISE petevts 
DESCRIPTION 
 "Boot Error - Non-bootable diskette left in drive" 

--#TYPE       "Boot Error Event" 
--#SUMMARY    "Boot Error - Non-bootable diskette left in drive" 
--#ARGUMENTS  {} 
--#SEVERITY   CRITICAL 

::= 1994497 

-- Boot Error - PXE Server not found 
trapPXEServerNotFound TRAP-TYPE 
ENTERPRISE petevts 
DESCRIPTION 
 "Boot Error - PXE Server not found" 

--#TYPE       "Boot Error Event" 
--#SUMMARY    "Boot Error - PXE Server not found" 
--#ARGUMENTS  {} 
--#SEVERITY   CRITICAL 

::= 1994498  
 
-- Boot Error - Invalid boot sector 
trapInvalidBootSector TRAP-TYPE 
ENTERPRISE petevts 
DESCRIPTION 
 "Boot Error - Invalid boot sector" 

--#TYPE       "Boot Error Event" 
--#SUMMARY    "Boot Error - Invalid boot sector" 
--#ARGUMENTS  {} 
--#SEVERITY   CRITICAL 

::= 1994499 

-- Boot Error - Timeout waiting for user selection of boot source 
trapTimeoutWaitingUserSelection TRAP-TYPE 
ENTERPRISE petevts 
DESCRIPTION 
 "Boot Error - Timeout waiting for user selection of boot source" 

--#TYPE       "Boot Error Event" 
--#SUMMARY    "Boot Error - Timeout waiting for user selection of boot source" 
--#ARGUMENTS  {} 
--#SEVERITY   INFORMATIONAL 

::= 1994500 
 
-- Bootable media found 
trapFoundBootableMedia TRAP-TYPE 
ENTERPRISE petevts 
DESCRIPTION 
 "Found bootable media" 

--#TYPE       "Boot Error Event" 
--#SUMMARY    "Found bootable media" 
--#ARGUMENTS  {} 
--#SEVERITY   INFORMATIONAL 

::= 1994624 

-- Bootable diskette Found 
trapFoundBootableDisketteInDrive TRAP-TYPE 
ENTERPRISE petevts 
DESCRIPTION 
 "Bootable diskette Found" 

--#TYPE       "Boot Error Event" 
--#SUMMARY    "Bootable diskette Found" 
--#ARGUMENTS  {} 
--#SEVERITY   INFORMATIONAL 

::= 1994625 

-- PXE Server  found 
trapPXEServerFound TRAP-TYPE 
ENTERPRISE petevts 
DESCRIPTION 
 "PXE Server found" 

--#TYPE       "Boot Error Event" 
--#SUMMARY    "PXE Server found" 
--#ARGUMENTS  {} 
--#SEVERITY   INFORMATIONAL 

::= 1994626  
 
-- Found valid boot sector 
trapFoundValidBootSector TRAP-TYPE 
ENTERPRISE petevts 
DESCRIPTION 
 "Found valid boot sector" 

--#TYPE       "Boot Error Event" 
--#SUMMARY    "Found Valid boot sector" 
--#ARGUMENTS  {} 
--#SEVERITY   INFORMATIONAL 

::= 1994627 

-- User selected boot source 
trapUserSelectedBootSource TRAP-TYPE 
ENTERPRISE petevts 
DESCRIPTION 
 "User selected boot source" 

--#TYPE       "Boot Error Event" 
--#SUMMARY    "User selected boot source" 
--#ARGUMENTS  {} 
--#SEVERITY   INFORMATIONAL 

::= 1994628 
 
-- ********************************************** 
-- *		OS Boot			* 
-- ********************************************** 
-- A: boot completed 
trapBootCompletedDirectoryA TRAP-TYPE 
ENTERPRISE petevts 
DESCRIPTION 
 "A: boot completed" 

--#TYPE       "OS Boot Event" 
--#SUMMARY    "A: boot completed" 
--#ARGUMENTS  {} 
--#SEVERITY   INFORMATIONAL 

::= 2060032 

 -- C: boot completed 
trapBootCompletedDirectoryC TRAP-TYPE 
ENTERPRISE petevts 
DESCRIPTION 
 "C: boot completed" 

--#TYPE       "OS Boot Event" 
--#SUMMARY    "C: boot completed" 
--#ARGUMENTS  {} 
--#SEVERITY   INFORMATIONAL 

::= 2060033 

 -- PXE boot completed 
trapPXEBootCompleted TRAP-TYPE 
ENTERPRISE petevts 
DESCRIPTION 
 "PXE boot completed" 

--#TYPE       "OS Boot Event" 
--#SUMMARY    "PXE boot completed" 
--#ARGUMENTS  {} 
--#SEVERITY   INFORMATIONAL 

::= 2060034 

 -- Diagnostic boot completed 
trapDiagnosticBootCompleted TRAP-TYPE 
ENTERPRISE petevts 
DESCRIPTION 
 "Diagnostic boot completed" 

--#TYPE       "OS Boot Event" 
--#SUMMARY    "Diagnostic boot completed" 
--#ARGUMENTS  {} 
--#SEVERITY   INFORMATIONAL 

::= 2060035 
 
  -- CDROM boot completed 
trapCDROMBootCompleted TRAP-TYPE 
ENTERPRISE petevts 
DESCRIPTION 
 "CDROM boot completed" 

--#TYPE       "OS Boot Event" 
--#SUMMARY    "CDROM boot completed" 
--#ARGUMENTS  {} 
--#SEVERITY   INFORMATIONAL 

::= 2060036 

 -- ROM boot completed 
trapROMBootCompleted TRAP-TYPE 
ENTERPRISE petevts 
DESCRIPTION 
 "ROM boot completed" 

--#TYPE       "OS Boot Event" 
--#SUMMARY    "ROM boot completed" 
--#ARGUMENTS  {} 
--#SEVERITY   INFORMATIONAL 

::= 2060037 

 -- Boot completed - boot device not specified 
trapBootCompletedUnknownSource TRAP-TYPE 
ENTERPRISE petevts 
DESCRIPTION 
 "Boot completed - boot device not specified" 

--#TYPE       "OS Boot Event" 
--#SUMMARY    "Boot completed - boot device not specified" 
--#ARGUMENTS  {} 
--#SEVERITY   INFORMATIONAL 

::= 2060038 
 
 -- A: boot incomplete 
trapBootIncompleteDirectoryA TRAP-TYPE 
ENTERPRISE petevts 
DESCRIPTION 
 "A: boot incomplete" 

--#TYPE       "OS Boot Event" 
--#SUMMARY    "A: boot incomplete" 
--#ARGUMENTS  {} 
--#SEVERITY   WARNING 

::= 2060160 

 -- C: boot incomplete 
trapBootIncompleteDirectoryC TRAP-TYPE 
ENTERPRISE petevts 
DESCRIPTION 
 "C: boot incomplete" 

--#TYPE       "OS Boot Event" 
--#SUMMARY    "C: boot incomplete" 
--#ARGUMENTS  {} 
--#SEVERITY   WARNING 

::= 2060161 

 -- PXE boot Incomplete 
trapPXEBootIncomplete TRAP-TYPE 
ENTERPRISE petevts 
DESCRIPTION 
 "PXE boot Incomplete" 

--#TYPE       "OS Boot Event" 
--#SUMMARY    "PXE boot Incomplete" 
--#ARGUMENTS  {} 
--#SEVERITY   WARNING 

::= 2060162 

 -- Diagnostic boot Incomplete 
trapDiagnosticBootIncomplete TRAP-TYPE 
ENTERPRISE petevts 
DESCRIPTION 
 "Diagnostic boot Incomplete" 

--#TYPE       "OS Boot Event" 
--#SUMMARY    "Diagnostic boot Incomplete" 
--#ARGUMENTS  {} 
--#SEVERITY   WARNING 

::= 2060163 
 
  -- CDROM boot Incomplete 
trapCDROMBootIncomplete TRAP-TYPE 
ENTERPRISE petevts 
DESCRIPTION 
 "CDROM boot Incomplete" 

--#TYPE       "OS Boot Event" 
--#SUMMARY    "CDROM boot Incomplete" 
--#ARGUMENTS  {} 
--#SEVERITY   WARNING 

::= 2060164 

 -- ROM boot Incomplete 
trapROMBootIncomplete TRAP-TYPE 
ENTERPRISE petevts 
DESCRIPTION 
 "ROM boot Incomplete" 

--#TYPE       "OS Boot Event" 
--#SUMMARY    "ROM boot Incomplete" 
--#ARGUMENTS  {} 
--#SEVERITY   WARNING 

::= 2060165 

 -- Boot Incomplete - boot device not specified 
trapBootIncompleteUnknownSource TRAP-TYPE 
ENTERPRISE petevts 
DESCRIPTION 
 "Boot Incomplete - boot device not specified" 

--#TYPE       "OS Boot Event" 
--#SUMMARY    "Boot Incomplete - boot device not specified" 
--#ARGUMENTS  {} 
--#SEVERITY   WARNING 

::= 2060166 
 
-- ********************************************** 
-- *		OS Stop / Shutdown			* 
-- ********************************************** 

 -- OS Stop / Shutdown - Stop during OS load / initialization 
trapOSStopDuringLoad TRAP-TYPE 
ENTERPRISE petevts 
DESCRIPTION 
 "OS Stop / Shutdown - Stop during OS load / initialization. Unexpected error uring system startup. Stopped waiting for input or power cycle/reset" 

--#TYPE       "OS Stop / Shutdown Event" 
--#SUMMARY    "OS Stop / Shutdown - Stop during OS load / initialization" 
--#ARGUMENTS  {} 
--#SEVERITY   CRITICAL 

::= 2125568 
 
  -- OS Stop / Shutdown - Run-time Critical Stop 
trapOSRuntimeCriticalStop TRAP-TYPE 
ENTERPRISE petevts 
DESCRIPTION 
 "OS Stop / Shutdown - Run-time Critical Stop" 

--#TYPE       "OS Stop / Shutdown Event" 
--#SUMMARY    "OS Stop / Shutdown - Run-time Critical Stop" 
--#ARGUMENTS  {} 
--#SEVERITY   CRITICAL 

::= 2125569 
 
-- OS Stop / Shutdown - Graceful Stop 
trapOSGracefulStop TRAP-TYPE 
ENTERPRISE petevts 
DESCRIPTION 
 "OS Stop / Shutdown - Graceful Stop (system powered up, but normal OS operation has shut down and system is awaiting reset pushbutton, powercycle or other external input)" 

--#TYPE       "OS Stop / Shutdown Event" 
--#SUMMARY    "OS Stop / Shutdown - Graceful Stop" 
--#ARGUMENTS  {} 
--#SEVERITY   INFORMATIONAL 

::= 2125570 
  
-- OS Stop / Shutdown - Graceful Shutdown 
trapOSGracefulShutdown TRAP-TYPE 
ENTERPRISE petevts 
DESCRIPTION 
 "OS Stop / Shutdown - Graceful Shutdown (system graceful power down by OS)" 

--#TYPE       "OS Stop / Shutdown Event" 
--#SUMMARY    "OS Stop / Shutdown - Graceful Shutdown" 
--#ARGUMENTS  {} 
--#SEVERITY   INFORMATIONAL 

::= 2125571 
 
-- OS Stop / Shutdown - Soft Shutdown initiated by PEF 
trapOSSoftShutdownInitiatedByPEF TRAP-TYPE 
ENTERPRISE petevts 
DESCRIPTION 
 "OS Stop / Shutdown - Soft Shutdown initiated by PEF" 

--#TYPE       "OS Stop / Shutdown Event" 
--#SUMMARY    "OS Stop / Shutdown - Soft Shutdown initiated by PEF" 
--#ARGUMENTS  {} 
--#SEVERITY   INFORMATIONAL 

::= 2125572 
 
-- OS Stop / Shutdown - Agent Not Responding 
trapOSAgentNotResponding TRAP-TYPE 
ENTERPRISE petevts 
DESCRIPTION 
 "OS Stop / Shutdown - Agent Not Responding" 

--#TYPE       "OS Stop / Shutdown Event" 
--#SUMMARY    "OS Stop / Shutdown - Agent Not Responding" 
--#ARGUMENTS  {} 
--#SEVERITY   CRITICAL 

::= 2125573 
 
  -- OS Stop / Shutdown - Stop during OS load / initialization Deasserted 
trapOSStopDuringLoadDeasserted TRAP-TYPE 
ENTERPRISE petevts 
DESCRIPTION 
 "OS Stop / Shutdown - power cycle/reset Done" 

--#TYPE       "OS Stop / Shutdown Event" 
--#SUMMARY    "OS Stop / Shutdown - Stop during OS load / initialization Deasserted" 
--#ARGUMENTS  {} 
--#SEVERITY   INFORMATIONAL 

::= 2125696 
 
  -- OS Stop / Shutdown - Run-time INFORMATIONAL Stop Deasserted 
trapOSRuntimeINFORMATIONALStopDeasserted TRAP-TYPE 
ENTERPRISE petevts 
DESCRIPTION 
 "OS Stop / Shutdown -Power Cycle/Reset Done" 

--#TYPE       "OS Stop / Shutdown Event" 
--#SUMMARY    "OS Stop / Shutdown - Run-time INFORMATIONAL Stop Deasserted" 
--#ARGUMENTS  {} 
--#SEVERITY   INFORMATIONAL 

::= 2125697 
 
-- OS Stop / Shutdown - Graceful Stop Deasserted 
trapOSGracefulStopDeasserted TRAP-TYPE 
ENTERPRISE petevts 
DESCRIPTION 
 "OS Stop / Shutdown - System powered up by reset pushbutton, powercycle or other external input" 

--#TYPE       "OS Stop / Shutdown Event" 
--#SUMMARY    "OS Stop / Shutdown - Graceful Stop Deasserted" 
--#ARGUMENTS  {} 
--#SEVERITY   INFORMATIONAL 

::= 2125698 
  
-- OS Stop / Shutdown - Graceful Shutdown Deasserted 
trapOSGracefulShutdownDeasserted TRAP-TYPE 
ENTERPRISE petevts 
DESCRIPTION 
 "OS Stop / Shutdown - System powered by reset pushbutton, powercycle or other external input" 

--#TYPE       "OS Stop / Shutdown Event" 
--#SUMMARY    "OS Stop / Shutdown - Graceful Shutdown Deasserted" 
--#ARGUMENTS  {} 
--#SEVERITY   INFORMATIONAL 

::= 2125699 
 
-- OS Stop / Shutdown - Soft Shutdown Deasserted 
trapOSSoftShutdownDeasserted TRAP-TYPE 
ENTERPRISE petevts 
DESCRIPTION 
 "OS Stop / Shutdown - System powered by reset pushbutton, powercycle or other external input" 

--#TYPE       "OS Stop / Shutdown Event" 
--#SUMMARY    "OS Stop / Shutdown - Soft Shutdown Deasserted" 
--#ARGUMENTS  {} 
--#SEVERITY   INFORMATIONAL 

::= 2125700 
 
-- OS Stop / Shutdown - Agent Started Responding 
trapOSAgentNotRespondingDeasserted TRAP-TYPE 
ENTERPRISE petevts 
DESCRIPTION 
 "OS Stop / Shutdown - Agent Started Responding" 

--#TYPE       "OS Stop / Shutdown Event" 
--#SUMMARY    "OS Stop / Shutdown - Agent Started Responding" 
--#ARGUMENTS  {} 
--#SEVERITY   INFORMATIONAL 

::= 2125701 
 
-- ********************************************** 
-- *		Slot / Connector			* 
-- ********************************************** 

-- Slot / Connector - Fault Status asserted 
trapSlotFaultStatusAsserted TRAP-TYPE 
ENTERPRISE petevts 
DESCRIPTION 
 "Slot / Connector - Fault Status asserted" 

--#TYPE       "Slot / Connector Event" 
--#SUMMARY    "Slot / Connector - Fault Status asserted" 
--#ARGUMENTS  {} 
--#SEVERITY   INFORMATIONAL 

::= 2191104 
 
-- Slot / Connector - Identify Status asserted 
trapSlotIdentifyStatusAsserted TRAP-TYPE 
ENTERPRISE petevts 
DESCRIPTION 
 "Slot / Connector - Identify Status asserted" 

--#TYPE       "Slot / Connector Event" 
--#SUMMARY    "Slot / Connector - Identify Status asserted" 
--#ARGUMENTS  {} 
--#SEVERITY   INFORMATIONAL 

::= 2191105 
 
-- Slot / Connector - Device installed/attached 
trapSlotDeviceInstalledOrAttached TRAP-TYPE 
ENTERPRISE petevts 
DESCRIPTION 
 "Slot / Connector - Device installed/attached" 

--#TYPE       "Slot / Connector Event" 
--#SUMMARY    "Slot / Connector - Device installed/attached" 
--#ARGUMENTS  {} 
--#SEVERITY   INFORMATIONAL 

::= 2191106 

-- Slot / Connector - Ready for Device Installation 
trapSlotReadyForDeviceInstallation TRAP-TYPE 
ENTERPRISE petevts 
DESCRIPTION 
 "Slot / Connector - Ready for Device Installation. Typically, this means that the slot power is off" 

--#TYPE       "Slot / Connector Event" 
--#SUMMARY    "Slot / Connector - Ready for Device Installation" 
--#ARGUMENTS  {} 
--#SEVERITY   INFORMATIONAL 

::= 2191107 
 
-- Slot / Connector - Ready for Device Removal 
trapSlotReadyForDeviceRemoval TRAP-TYPE 
ENTERPRISE petevts 
DESCRIPTION 
 "Slot / Connector - Ready for Device Removal. Typically, this means that the slot power is off" 

--#TYPE       "Slot / Connector Event" 
--#SUMMARY    "Slot / Connector - Ready for Device Removal" 
--#ARGUMENTS  {} 
--#SEVERITY   INFORMATIONAL 

::= 2191108 
 
-- Slot / Connector - Slot Power is Off 
trapSlotPowerIsOff TRAP-TYPE 
ENTERPRISE petevts 
DESCRIPTION 
 "Slot / Connector - Slot Power is Off" 

--#TYPE       "Slot / Connector Event" 
--#SUMMARY    "Slot / Connector - Slot Power is Off" 
--#ARGUMENTS  {} 
--#SEVERITY   INFORMATIONAL 

::= 2191109 
 
-- Slot / Connector - Device Removal Request 
trapSlotDeviceRemovalRequest TRAP-TYPE 
ENTERPRISE petevts 
DESCRIPTION 
 "Slot / Connector - Device Removal Request" 

--#TYPE       "Slot / Connector Event" 
--#SUMMARY    "Slot / Connector - Device Removal Request" 
--#ARGUMENTS  {} 
--#SEVERITY   INFORMATIONAL 

::= 2191110 
 
-- Slot / Connector - Interlock asserted 
trapSlotInterlockAsserted TRAP-TYPE 
ENTERPRISE petevts 
DESCRIPTION 
 "Slot / Connector - Interlock asserted" 

--#TYPE       "Slot / Connector Event" 
--#SUMMARY    "Slot / Connector - Interlock asserted" 
--#ARGUMENTS  {} 
--#SEVERITY   INFORMATIONAL 

::= 2191111 
 
-- Slot / Connector - Disabled 
trapSlotDisabled TRAP-TYPE 
ENTERPRISE petevts 
DESCRIPTION 
 "Slot / Connector - Disabled" 

--#TYPE       "Slot / Connector Event" 
--#SUMMARY    "Slot / Connector - Disabled" 
--#ARGUMENTS  {} 
--#SEVERITY   INFORMATIONAL 

::= 2191112 
 
-- Slot / Connector - holds spare device 
trapSlotHoldsSpareDevice TRAP-TYPE 
ENTERPRISE petevts 
DESCRIPTION 
 "Slot / Connector - holds spare device" 

--#TYPE       "Slot / Connector Event" 
--#SUMMARY    "Slot / Connector - holds spare device" 
--#ARGUMENTS  {} 
--#SEVERITY   INFORMATIONAL 

::= 2191113 
 
-- Slot / Connector - Fault Status Deasserted 
trapSlotFaultStatusDeasserted TRAP-TYPE 
ENTERPRISE petevts 
DESCRIPTION 
 "Slot / Connector - Fault Status Deasserted" 

--#TYPE       "Slot / Connector Event" 
--#SUMMARY    "Slot / Connector - Fault Status Deasserted" 
--#ARGUMENTS  {} 
--#SEVERITY   INFORMATIONAL 

::= 2191232 
 
-- Slot / Connector - Identify Status Deasserted 
trapSlotIdentifyStatusDeasserted TRAP-TYPE 
ENTERPRISE petevts 
DESCRIPTION 
 "Slot / Connector - Identify Status Deasserted" 

--#TYPE       "Slot / Connector Event" 
--#SUMMARY    "Slot / Connector - Identify Status Deasserted" 
--#ARGUMENTS  {} 
--#SEVERITY   INFORMATIONAL 

::= 2191233 
 
-- Slot / Connector - Device Removed 
trapSlotDeviceRemoved TRAP-TYPE 
ENTERPRISE petevts 
DESCRIPTION 
 "Slot / Connector - Device Uninstalled/Removed" 

--#TYPE       "Slot / Connector Event" 
--#SUMMARY    "Slot / Connector - Device Uninstalled/Removed" 
--#ARGUMENTS  {} 
--#SEVERITY   INFORMATIONAL 

::= 2191234 

-- Slot / Connector - Not Ready for Device Installation 
trapSlotNotReadyForDeviceInstallation TRAP-TYPE 
ENTERPRISE petevts 
DESCRIPTION 
 "Slot / Connector - Not Ready for Device Installation. Typically, this means that the slot power is on" 

--#TYPE       "Slot / Connector Event" 
--#SUMMARY    "Slot / Connector - Not Ready for Device Installation" 
--#ARGUMENTS  {} 
--#SEVERITY   INFORMATIONAL 

::= 2191235 
 
-- Slot / Connector - Not Ready for Device Removal 
trapSlotNotReadyForDeviceRemoval TRAP-TYPE 
ENTERPRISE petevts 
DESCRIPTION 
 "Slot / Connector - Not Ready for Device Removal. Typically, this means that the slot power is on" 

--#TYPE       "Slot / Connector Event" 
--#SUMMARY    "Slot / Connector - Ready for Device Removal" 
--#ARGUMENTS  {} 
--#SEVERITY   INFORMATIONAL 

::= 2191236 
 
-- Slot / Connector - Slot Power is On 
trapSlotPowerIsOn TRAP-TYPE 
ENTERPRISE petevts 
DESCRIPTION 
 "Slot / Connector - Slot Power is On" 

--#TYPE       "Slot / Connector Event" 
--#SUMMARY    "Slot / Connector - Slot Power is On" 
--#ARGUMENTS  {} 
--#SEVERITY   INFORMATIONAL 

::= 2191237 
 
-- Slot / Connector - Device Removal Request Processed 
trapSlotDeviceRemovalRequestProcessed TRAP-TYPE 
ENTERPRISE petevts 
DESCRIPTION 
 "Slot / Connector - Device Removal Request Processed" 

--#TYPE       "Slot / Connector Event" 
--#SUMMARY    "Slot / Connector - Device Removal Request Processed" 
--#ARGUMENTS  {} 
--#SEVERITY   INFORMATIONAL 

::= 2191238 
 
-- Slot / Connector - Interlock Deasserted 
trapSlotInterlockDeasserted TRAP-TYPE 
ENTERPRISE petevts 
DESCRIPTION 
 "Slot / Connector - Interlock Deasserted" 

--#TYPE       "Slot / Connector Event" 
--#SUMMARY    "Slot / Connector - Interlock Deasserted" 
--#ARGUMENTS  {} 
--#SEVERITY   INFORMATIONAL 

::= 2191239 
 
-- Slot / Connector - Enabled 
trapSlotEnabled TRAP-TYPE 
ENTERPRISE petevts 
DESCRIPTION 
 "Slot / Connector - Enabled" 

--#TYPE       "Slot / Connector Event" 
--#SUMMARY    "Slot / Connector - Enabled" 
--#ARGUMENTS  {} 
--#SEVERITY   INFORMATIONAL 

::= 2191240 
 
-- Slot / Connector - frees spare device 
trapSlotFreesSpareDevice TRAP-TYPE 
ENTERPRISE petevts 
DESCRIPTION 
 "Slot / Connector - frees spare device" 

--#TYPE       "Slot / Connector Event" 
--#SUMMARY    "Slot / Connector - frees spare device" 
--#ARGUMENTS  {} 
--#SEVERITY   INFORMATIONAL 

::= 2191241 
 
-- ********************************************** 
-- *		System ACPI Power State			* 
-- ********************************************** 
-- System ACPI Power State - S0 / G0 working 
trapACPIStateS0Working TRAP-TYPE 
ENTERPRISE petevts 
DESCRIPTION 
 "System ACPI Power State - S0 / G0 - Working" 

--#TYPE       "System ACPI Power State Event" 
--#SUMMARY    "System ACPI Power State - S0 / G0 " 
--#ARGUMENTS  {} 
--#SEVERITY   INFORMATIONAL 

::= 2256640 
 
-- System ACPI Power State - S1 
trapACPIStateS1 TRAP-TYPE 
ENTERPRISE petevts 
DESCRIPTION 
 "System ACPI Power State - S1 - sleeping with system h/w & processor context maintained" 

--#TYPE       "System ACPI Power State Event" 
--#SUMMARY    "System ACPI Power State - S1" 
--#ARGUMENTS  {} 
--#SEVERITY   INFORMATIONAL 

::= 2256641 
 
-- System ACPI Power State - S2  
trapACPIStateS2 TRAP-TYPE 
ENTERPRISE petevts 
DESCRIPTION 
 "System ACPI Power State - S2 sleeping, processor context lost" 

--#TYPE       "System ACPI Power State Event" 
--#SUMMARY    "System ACPI Power State - S2 " 
--#ARGUMENTS  {} 
--#SEVERITY   INFORMATIONAL 

::= 2256642 
 
-- System ACPI Power State - S3 
trapACPIStateS3 TRAP-TYPE 
ENTERPRISE petevts 
DESCRIPTION 
 "System ACPI Power State - S3" 

--#TYPE       "System ACPI Power State Event" 
--#SUMMARY    "System ACPI Power State - S3 - sleeping, processor & h/w context lost, memory retained" 
--#ARGUMENTS  {} 
--#SEVERITY   INFORMATIONAL 

::= 2256643 
 
-- System ACPI Power State - S4 
trapACPIStateS4 TRAP-TYPE 
ENTERPRISE petevts 
DESCRIPTION 
 "System ACPI Power State - S4 - non-volatile sleep / suspend-to disk" 

--#TYPE       "System ACPI Power State Event" 
--#SUMMARY    "System ACPI Power State - S4" 
--#ARGUMENTS  {} 
--#SEVERITY   INFORMATIONAL 

::= 2256644 
 
-- System ACPI Power State - S5 / G2 
trapACPIStateS5 TRAP-TYPE 
ENTERPRISE petevts 
DESCRIPTION 
 "System ACPI Power State - S5 / G2 - soft-off" 

--#TYPE       "System ACPI Power State Event" 
--#SUMMARY    "System ACPI Power State - S5 / G2" 
--#ARGUMENTS  {} 
--#SEVERITY   INFORMATIONAL 

::= 2256645 
 
-- System ACPI Power State - S4 / S5 soft-off 
trapACPIStateS4OrS5SoftOff TRAP-TYPE 
ENTERPRISE petevts 
DESCRIPTION 
 "System ACPI Power State - S4 / S5 soft-off, particular S4 / S5 state cannot be determi" 

--#TYPE       "System ACPI Power State Event" 
--#SUMMARY    "System ACPI Power State - S4 / S5 soft-off" 
--#ARGUMENTS  {} 
--#SEVERITY   INFORMATIONAL 

::= 2256646 
 
-- System ACPI Power State - G3 
trapACPIStateG3 TRAP-TYPE 
ENTERPRISE petevts 
DESCRIPTION 
 "System ACPI Power State - G3 - Mechanical Off" 

--#TYPE       "System ACPI Power State Event" 
--#SUMMARY    "System ACPI Power State - G3" 
--#ARGUMENTS  {} 
--#SEVERITY   INFORMATIONAL 

::= 2256647 
 
-- System ACPI Power State - Sleeping in an S1, S2, or S3 states 
trapACPISleepingInUnknownState TRAP-TYPE 
ENTERPRISE petevts 
DESCRIPTION 
 "System ACPI Power State - Sleeping in an S1, S2, or S3 states" 

--#TYPE       "System ACPI Power State Event" 
--#SUMMARY    "System ACPI Power State - Sleeping in an S1, S2, or S3 states" 
--#ARGUMENTS  {} 
--#SEVERITY   INFORMATIONAL 

::= 2256648 
 
-- System ACPI Power State - G1  
trapACPIStateG1 TRAP-TYPE 
ENTERPRISE petevts 
DESCRIPTION 
 "System ACPI Power State - G1 - sleeping (S1-S4 state cannot be determined)" 

--#TYPE       "System ACPI Power State Event" 
--#SUMMARY    "System ACPI Power State - G1" 
--#ARGUMENTS  {} 
--#SEVERITY   INFORMATIONAL 

::= 2256649 
 
-- System ACPI Power State - S5 entered by override 
trapACPIStateS5ByOverride TRAP-TYPE 
ENTERPRISE petevts 
DESCRIPTION 
 "System ACPI Power State - S5 entered by override" 

--#TYPE       "System ACPI Power State Event" 
--#SUMMARY    "System ACPI Power State - S5 entered by override" 
--#ARGUMENTS  {} 
--#SEVERITY   INFORMATIONAL 

::= 2256650 
 
-- System ACPI Power State - Legacy ON state 
trapACPILegacyONState TRAP-TYPE 
ENTERPRISE petevts 
DESCRIPTION 
 "System ACPI Power State - Legacy ON state" 

--#TYPE       "System ACPI Power State Event" 
--#SUMMARY    "System ACPI Power State - Legacy ON state" 
--#ARGUMENTS  {} 
--#SEVERITY   INFORMATIONAL 

::= 2256651 
 
-- System ACPI Power State - Legacy OFF state 
trapACPILegacyOFFState TRAP-TYPE 
ENTERPRISE petevts 
DESCRIPTION 
 "System ACPI Power State - Legacy OFF state" 

--#TYPE       "System ACPI Power State Event" 
--#SUMMARY    "System ACPI Power State - Legacy OFF state" 
--#ARGUMENTS  {} 
--#SEVERITY   INFORMATIONAL 

::= 2256652 
 
-- System ACPI Power State - Unknown 
trapACPIStateUnknown TRAP-TYPE 
ENTERPRISE petevts 
DESCRIPTION 
 "System ACPI Power State - Unknown" 

--#TYPE       "System ACPI Power State Event" 
--#SUMMARY    "System ACPI Power State - Unknown" 
--#ARGUMENTS  {} 
--#SEVERITY   INFORMATIONAL 

::= 2256654 
 
-- ********************************************** 
-- *		Watchdog 2			* 
-- ********************************************** 
-- Watchdog timer expired 
trapWatchdogTimerExpired TRAP-TYPE 
ENTERPRISE petevts 
DESCRIPTION  
 "Watchdog timer expired, status only (no action, no interrupt)" 

--#TYPE       "Watchdog Event" 
--#SUMMARY    "Watchdog timer expired" 
--#ARGUMENTS  {} 
--#SEVERITY   WARNING 

::=  2322176 
 
-- Watchdog reset event 
trapWatchdogReset TRAP-TYPE 
ENTERPRISE petevts 
DESCRIPTION  
 "Watchdog Reset" 

--#TYPE       "Watchdog Event" 
--#SUMMARY    "Watchdog Reset" 
--#ARGUMENTS  {} 
--#SEVERITY   CRITICAL 

::=  2322177 

-- Watchdog power down event 
trapWatchdogPowerDown TRAP-TYPE 
ENTERPRISE petevts 
DESCRIPTION  
 "Watchdog Power Down" 

--#TYPE       "Watchdog Event" 
--#SUMMARY    "Watchdog Power Down" 
--#ARGUMENTS  {} 
--#SEVERITY   CRITICAL 

::=  2322178 
 
-- Watchdog power cycle event 
trapWatchdogPowerCycle TRAP-TYPE 
ENTERPRISE petevts 
DESCRIPTION  
 "Watchdog Power Cycle" 

--#TYPE       "Watchdog Event" 
--#SUMMARY    "Watchdog Power cycle" 
--#ARGUMENTS  {} 
--#SEVERITY   WARNING 

::= 2322179 

-- Watchdog Timer interrupt 
trapWatchdogTimerInterrupt TRAP-TYPE 
ENTERPRISE petevts 
DESCRIPTION  
 "Watchdog Timer interrupt" 

--#TYPE       "Watchdog Event" 
--#SUMMARY    "Watchdog Timer interrupt" 
--#ARGUMENTS  {} 
--#SEVERITY   INFORMATIONAL 

::= 2322184 
 
-- Watchdog timer Reset 
trapWatchdogTimerExpiredDeasserted TRAP-TYPE 
ENTERPRISE petevts 
DESCRIPTION  
 "Watchdog timer Reset" 

--#TYPE       "Watchdog Event" 
--#SUMMARY    "Watchdog timer reset" 
--#ARGUMENTS  {} 
--#SEVERITY   WARNING 

::=  2322304 
 
-- Watchdog reset event Deasserted 
trapWatchdogResetDeasserted TRAP-TYPE 
ENTERPRISE petevts 
DESCRIPTION  
 "Watchdog Reset Deasserted" 

--#TYPE       "Watchdog Event" 
--#SUMMARY    "Watchdog Reset Deasserted" 
--#ARGUMENTS  {} 
--#SEVERITY   CRITICAL 

::=  2322305 

-- Watchdog power down event Deasserted 
trapWatchdogPowerDownDeasserted TRAP-TYPE 
ENTERPRISE petevts 
DESCRIPTION  
 "Watchdog Power Down Deasserted" 

--#TYPE       "Watchdog Event" 
--#SUMMARY    "Watchdog Power Down Deasserted" 
--#ARGUMENTS  {} 
--#SEVERITY   CRITICAL 

::=  2322306 
 
-- Watchdog power cycle event Deasserted 
trapWatchdogPowerCycleDeasserted TRAP-TYPE 
ENTERPRISE petevts 
DESCRIPTION  
 "Watchdog Power Cycle Deasserted" 

--#TYPE       "Watchdog Event" 
--#SUMMARY    "Watchdog Power cycle Deasserted" 
--#ARGUMENTS  {} 
--#SEVERITY   WARNING 

::= 2322307 

-- Watchdog Timer interrupt Deasserted 
trapWatchdogTimerInterruptDeasserted TRAP-TYPE 
ENTERPRISE petevts 
DESCRIPTION  
 "Watchdog Timer interrupt Deasserted" 

--#TYPE       "Watchdog Event" 
--#SUMMARY    "Watchdog Timer interrupt Deasserted" 
--#ARGUMENTS  {} 
--#SEVERITY   INFORMATIONAL 

::= 2322312 
 
 
-- ********************************************** 
-- *		Platform Alert			* 
-- ********************************************** 
-- Platform Alert - platform generated page 
trapPlatformGeneratedPage TRAP-TYPE 
ENTERPRISE petevts 
DESCRIPTION  
 "Platform Alert - platform generated page" 

--#TYPE       "Platform Alert Event" 
--#SUMMARY    "Platform Alert- platform generated page" 
--#ARGUMENTS  {} 
--#SEVERITY   INFORMATIONAL 

::= 2387712 

-- Platform Alert platform generated LAN alert 
trapPlatformGeneratedLANAlert TRAP-TYPE 
ENTERPRISE petevts 
DESCRIPTION  
 "Platform Alert - platform generated LAN alert" 

--#TYPE       "Platform Alert Event" 
--#SUMMARY    "Platform Alert- platform generated LAN alert" 
--#ARGUMENTS  {} 
--#SEVERITY   INFORMATIONAL 

::= 2387713 
 
-- Platform Alert Platform Event Trap generated 
trapPlatformPETFormatTrap TRAP-TYPE 
ENTERPRISE petevts 
DESCRIPTION  
 "Platform Alert - Platform Event Trap generated" 

--#TYPE       "Platform Alert Event" 
--#SUMMARY    "Platform Alert-  Platform Event Trap generated (formatted per IPMI PET specification)" 
--#ARGUMENTS  {} 
--#SEVERITY   INFORMATIONAL 

::= 2387714 
 
-- Platform Alert platform generated SNMP trap, OEM format 
trapPlatformOEMFormatTrap TRAP-TYPE 
ENTERPRISE petevts 
DESCRIPTION  
 "Platform Alert - platform generated SNMP trap, OEM format" 

--#TYPE       "Platform Alert Event" 
--#SUMMARY    "Platform Alert- platform generated SNMP trap, OEM format" 
--#ARGUMENTS  {} 
--#SEVERITY   INFORMATIONAL 

::= 2387715 
 
 
-- ********************************************** 
-- *		Entity Presence			* 
-- ********************************************** 
-- A device is present or has been removed 
trapEntityPresenceDeviceRemovedOrAbsent TRAP-TYPE 
ENTERPRISE petevts 
DESCRIPTION  
 "A device is absent or has been removed." 

--#TYPE       "Entity Presence Event" 
--#SUMMARY    "A device is absent or has been removed." 
--#ARGUMENTS  {} 
--#SEVERITY   CRITICAL 

::= 2426880 

-- A device is present or has been inserted 
trapEntityPresenceDeviceInsertedOrPresent TRAP-TYPE 
ENTERPRISE petevts 
DESCRIPTION  
 "A device is present or has been inserted." 

--#TYPE       "Entity Presence Event" 
--#SUMMARY    "A device is present or has been inserted." 
--#ARGUMENTS  {} 
--#SEVERITY   INFORMATIONAL 

::= 2426881 

-- Entity Present 
trapEntityPresent TRAP-TYPE 
ENTERPRISE petevts 
DESCRIPTION  
 "The Entity identified by the Entity ID for the sensor is present." 

--#TYPE       "Entity Presence Event" 
--#SUMMARY    "Entity Present" 
--#ARGUMENTS  {} 
--#SEVERITY   INFORMATIONAL 

::= 2453248 
 
-- Entity Absent. 
trapEntityAbsent TRAP-TYPE 
ENTERPRISE petevts 
DESCRIPTION  
 "The Entity identified by the Entity ID for the sensor is Absent." 

--#TYPE       "Entity Presence Event" 
--#SUMMARY    "Entity Absent." 
--#ARGUMENTS  {} 
--#SEVERITY   INFORMATIONAL 

::= 2453249 

 -- Entity Disabled.. 
trapEntityDisabled TRAP-TYPE 
ENTERPRISE petevts 
DESCRIPTION  
 "The Entity identified by the Entity ID for the sensor is Disabled." 

--#TYPE       "Entity Presence Event" 
--#SUMMARY    "Entity Disabled." 
--#ARGUMENTS  {} 
--#SEVERITY   INFORMATIONAL 

::= 2453250 
 
 
-- ********************************************** 
-- *		Monitor ASIC / IC			* 
-- ********************************************** 
-- Monitor ASIC / IC Failure Deasserted 
trapMonitoASICFailureDeasserted TRAP-TYPE 
ENTERPRISE petevts 
DESCRIPTION  
 "Monitor ASIC / IC Failure Deasserted" 

--#TYPE       "Monitor ASIC / IC Event" 
--#SUMMARY    "Monitor ASIC / IC Failure Deasserted" 
--#ARGUMENTS  {} 
--#SEVERITY   INFORMATIONAL 

::= 2491392 
 
-- Monitor ASIC / IC Failure Asserted 
trapMonitoASICFailureAsserted TRAP-TYPE 
ENTERPRISE petevts 
DESCRIPTION  
 "Monitor ASIC / IC Failure Asserted" 

--#TYPE       "Monitor ASIC / IC Event" 
--#SUMMARY    "Monitor ASIC / IC Failure Asserted" 
--#ARGUMENTS  {} 
--#SEVERITY   MAJOR 

::= 2491393 
 
-- ********************************************** 
-- *		Management Subsystem Health			* 
-- ********************************************** 
-- Sensor access degraded or unavailable 
trapSensorAccessDegradedOrUnavailable TRAP-TYPE 
ENTERPRISE petevts 
DESCRIPTION  
 "Sensor access degraded or unavailable" 

--#TYPE       "Management Subsystem Health Event" 
--#SUMMARY    "Sensor access degraded or unavailable" 
--#ARGUMENTS  {} 
--#SEVERITY   MAJOR 

::= 2649856 
 
-- Controller access degraded or unavailable 
trapControllerAccessDegradedOrUnavailable TRAP-TYPE 
ENTERPRISE petevts 
DESCRIPTION  
 "Controller access degraded or unavailable" 

--#TYPE       "Management Subsystem Health Event" 
--#SUMMARY    "Controller access degraded or unavailable" 
--#ARGUMENTS  {} 
--#SEVERITY   MAJOR 

::= 2649857 
 
-- Management controller off-line 
trapManagementControllerOffline TRAP-TYPE 
ENTERPRISE petevts 
DESCRIPTION  
 "Management controller off-line" 

--#TYPE       "Management Subsystem Health Event" 
--#SUMMARY    "Management controller off-line" 
--#ARGUMENTS  {} 
--#SEVERITY   MAJOR 

::= 2649858 
 
-- Management controller Unavailable 
trapManagementControllerUnavailable TRAP-TYPE 
ENTERPRISE petevts 
DESCRIPTION  
 "Management controller Unavailable" 

--#TYPE       "Management Subsystem Health Event" 
--#SUMMARY    "Management controller Unavailable" 
--#ARGUMENTS  {} 
--#SEVERITY   MAJOR 

::= 2649859 
 
-- Sensor failure 
trapSensorFailure TRAP-TYPE 
ENTERPRISE petevts 
DESCRIPTION  
 "Sensor failure" 

--#TYPE       "Management Subsystem Health Event" 
--#SUMMARY    "Sensor failure" 
--#ARGUMENTS  {} 
--#SEVERITY   MAJOR 

::= 2649860 
 
-- FRU failure 
trapFRUFailure TRAP-TYPE 
ENTERPRISE petevts 
DESCRIPTION  
 "FRU failure" 

--#TYPE       "Management Subsystem Health Event" 
--#SUMMARY    "FRU failure" 
--#ARGUMENTS  {} 
--#SEVERITY   MAJOR 

::= 2649861 
 
-- Sensor access available 
trapSensorAccessAvailable TRAP-TYPE 
ENTERPRISE petevts 
DESCRIPTION  
 "Sensor access Available" 

--#TYPE       "Management Subsystem Health Event" 
--#SUMMARY    "Sensor access Available" 
--#ARGUMENTS  {} 
--#SEVERITY   INFORMATIONAL 

::= 2649984 
 
-- Controller access Available 
trapControllerAccessAvailable TRAP-TYPE 
ENTERPRISE petevts 
DESCRIPTION  
 "Controller access Available" 

--#TYPE       "Management Subsystem Health Event" 
--#SUMMARY    "Controller access Available" 
--#ARGUMENTS  {} 
--#SEVERITY   INFORMATIONAL 

::= 2649985 
 
-- Management controller online 
trapManagementControllerOnline TRAP-TYPE 
ENTERPRISE petevts 
DESCRIPTION  
 "Management controller online" 

--#TYPE       "Management Subsystem Health Event" 
--#SUMMARY    "Management controller online" 
--#ARGUMENTS  {} 
--#SEVERITY   INFORMATIONAL 

::= 2649986 
 
-- Management controller Available 
trapManagementControllerAvailable TRAP-TYPE 
ENTERPRISE petevts 
DESCRIPTION  
 "Management controller Available" 

--#TYPE       "Management Subsystem Health Event" 
--#SUMMARY    "Management controller Available" 
--#ARGUMENTS  {} 
--#SEVERITY   INFORMATIONAL 

::= 2649987 
 
-- Sensor failure Deasserted 
trapSensorFailureDeasserted TRAP-TYPE 
ENTERPRISE petevts 
DESCRIPTION  
 "Sensor failure Deasserted" 

--#TYPE       "Management Subsystem Health Event" 
--#SUMMARY    "Sensor failure Deasserted" 
--#ARGUMENTS  {} 
--#SEVERITY   INFORMATIONAL 

::= 2649988 
 
-- FRU failure Deasserted 
trapFRUFailureDeasserted TRAP-TYPE 
ENTERPRISE petevts 
DESCRIPTION  
 "FRU failure Deasserted" 

--#TYPE       "Management Subsystem Health Event" 
--#SUMMARY    "FRU failure Deasserted" 
--#ARGUMENTS  {} 
--#SEVERITY   INFORMATIONAL 

::= 2649989 
 
-- ********************************************** 
-- *		Battery			* 
-- ********************************************** 

-- Battery low 
trapBatteryLowAssert TRAP-TYPE 
ENTERPRISE petevts 
DESCRIPTION  
 "Battery low" 

--#TYPE       "Battery Event" 
--#SUMMARY    "Battery low" 
--#ARGUMENTS  {} 
--#SEVERITY   WARNING 

::= 2715392 
 
-- Battery failed 
trapBatteryFailed TRAP-TYPE 
ENTERPRISE petevts 
DESCRIPTION  
 "Battery Failed" 

--#TYPE       "Battery Event" 
--#SUMMARY    "Battery Failed" 
--#ARGUMENTS  {} 
--#SEVERITY   CRITICAL 

::= 2715393 
 
-- Battery presence detected 
trapBatteryPresenceDetected TRAP-TYPE 
ENTERPRISE petevts 
DESCRIPTION  
 "Battery presence detected" 

--#TYPE       "Battery Event" 
--#SUMMARY    "Battery presence detected" 
--#ARGUMENTS  {} 
--#SEVERITY   INFORMATIONAL 

::= 2715394 
 
-- ********************************************** 
-- *		Session Audit			* 
-- ********************************************** 

-- Session Activated 
trapSessionActivated TRAP-TYPE 
ENTERPRISE petevts 
DESCRIPTION  
 "Session Activated" 

--#TYPE       "Session Audit Event" 
--#SUMMARY    "Session Activated" 
--#ARGUMENTS  {} 
--#SEVERITY   INFORMATIONAL 

::= 2780928 

-- Session Deactivated 
trapSessionDeactivated TRAP-TYPE 
ENTERPRISE petevts 
DESCRIPTION  
 "Session Deactivated" 

--#TYPE       "Session Audit Event" 
--#SUMMARY    "Session Deactivated" 
--#ARGUMENTS  {} 
--#SEVERITY   WARNING 

::= 2780929 
 
-- Session Invalid Username or Password 
trapSessionInvalidUsernameOrPassword TRAP-TYPE 
ENTERPRISE petevts 
DESCRIPTION  
 "Session Invalid Username or Password" 

--#TYPE       "Session Audit Event" 
--#SUMMARY    "Session Invalid Username or Password" 
--#ARGUMENTS  {} 
--#SEVERITY   WARNING 

::= 2780930 
 
-- Session Invalid password disable 
trapSessionUserAccessDisabled TRAP-TYPE 
ENTERPRISE petevts 
DESCRIPTION  
 "A user's access has been disabled due to a series of bad password attempts" 

--#TYPE       "Session Audit Event" 
--#SUMMARY    "Session Invalid password disable" 
--#ARGUMENTS  {} 
--#SEVERITY   WARNING 

::= 2780931 

-- ********************************************** 
-- *		Version Change			* 
-- ********************************************** 

-- Hardware Version change detected 
trapHardwareVersionChangeDetected TRAP-TYPE 
ENTERPRISE petevts 
DESCRIPTION  
 "Hardware Version change detected with associated Entity" 

--#TYPE       "Version Change Event" 
--#SUMMARY    "Hardware Version change detected" 
--#ARGUMENTS  {} 
--#SEVERITY   INFORMATIONAL 

::= 2846464 
 
-- Firmware or Software version change detected 
trapFirmwareOrSoftwareVersionChangeDetected TRAP-TYPE 
ENTERPRISE petevts 
DESCRIPTION  
 "Firmware or Software version change detected with associated Entity" 

--#TYPE       "Version Change Event" 
--#SUMMARY    "Firmware or Software version change detected" 
--#ARGUMENTS  {} 
--#SEVERITY   INFORMATIONAL 

::= 2846465 
 
-- Hardware Incombabaility detected 
trapHardwareVersionIncombabailityDetected TRAP-TYPE 
ENTERPRISE petevts 
DESCRIPTION  
 "Hardware Incombabaility detected with associated Entity" 

--#TYPE       "Version Change Event" 
--#SUMMARY    "Hardware Incombabaility detected" 
--#ARGUMENTS  {} 
--#SEVERITY   INFORMATIONAL 

::= 2846466 
 
-- Firmware Or Software Version Incompatibility detected 
trapFirmwareOrSoftwareVersionIncompatibilityDetected TRAP-TYPE 
ENTERPRISE petevts 
DESCRIPTION  
 "Firmware Or Software Version Incompatibility detected with associated Entity" 

--#TYPE       "Version Change Event" 
--#SUMMARY    "Firmware Or SoftwareVersion Incompatibility detected" 
--#ARGUMENTS  {} 
--#SEVERITY   INFORMATIONAL 

::= 2846467 
 
-- Entity is of an invalid or unsupported hardware version 
trapEntityInvalidOrUnsupportedHardware  TRAP-TYPE 
ENTERPRISE petevts 
DESCRIPTION  
 "Entity is of an invalid or unsupported hardware version" 

--#TYPE       "Version Change Event" 
--#SUMMARY    "Entity is of an invalid or unsupported hardware version" 
--#ARGUMENTS  {} 
--#SEVERITY   INFORMATIONAL 

::= 2846468 
 
-- Entity contains an invalid or unsupported firmware or software version 
trapEntityInvalidOrUnsupportedSwOrFw TRAP-TYPE 
ENTERPRISE petevts 
DESCRIPTION  
 "Entity contains an invalid or unsupported firmware or software version" 

--#TYPE       "Version Change Event" 
--#SUMMARY    "Entity contains an invalid or unsupported firmware or software version" 
--#ARGUMENTS  {} 
--#SEVERITY   INFORMATIONAL 

::= 2846469 
 
-- Hardware Change detected with associated Entity was successful 
trapHardwareChangeSuccessful TRAP-TYPE 
ENTERPRISE petevts 
DESCRIPTION  
 "Hardware Change detected with associated Entity was successful" 

--#TYPE       "Version Change Event" 
--#SUMMARY    "Hardware Change detected with associated Entity was successful" 
--#ARGUMENTS  {} 
--#SEVERITY   INFORMATIONAL 

::= 2846470 
 
-- Software or F/W Change detected with associated Entity was successful. 
trapSwOrFwChangeSuccessful TRAP-TYPE 
ENTERPRISE petevts 
DESCRIPTION  
 "Software or F/W Change detected with associated Entity was successful." 

--#TYPE       "Version Change Event" 
--#SUMMARY    "Software or F/W Change detected with associated Entity was successful." 
--#ARGUMENTS  {} 
--#SEVERITY   INFORMATIONAL 

::= 2846471 
 
 -- Hardware Change detected with associated Entity was not successful 
trapHardwareChangeNotSuccessful TRAP-TYPE 
ENTERPRISE petevts 
DESCRIPTION  
 "Hardware Change detected with associated Entity was not successful" 

--#TYPE       "Version Change Event" 
--#SUMMARY    "Hardware Change detected with associated Entity was not successful" 
--#ARGUMENTS  {} 
--#SEVERITY   INFORMATIONAL 

::= 2846598 
 
-- Software or F/W Change detected with associated Entity was not successful. 
trapSwOrFwChangeNotSuccessful TRAP-TYPE 
ENTERPRISE petevts 
DESCRIPTION  
 "Software or F/W Change detected with associated Entity was not successful." 

--#TYPE       "Version Change Event" 
--#SUMMARY    "Software or F/W Change detected with associated Entity was not successful." 
--#ARGUMENTS  {} 
--#SEVERITY   INFORMATIONAL 

::= 2846599 
 
-- ********************************************** 
-- *		FRU State			* 
-- ********************************************** 

-- FRU Not Installed 
trapFRUNotInstalled TRAP-TYPE 
ENTERPRISE petevts 
DESCRIPTION  
 "FRU Not Installed" 

--#TYPE       "FRU State Event" 
--#SUMMARY    "FRU Not Installed" 
--#ARGUMENTS  {} 
--#SEVERITY   INFORMATIONAL 

::= 2912000 
 
 -- FRU Inactive 
trapFRUInactive TRAP-TYPE 
ENTERPRISE petevts 
DESCRIPTION  
 "FRU Inactive" 

--#TYPE       "FRU State Event" 
--#SUMMARY    "FRU Inactive" 
--#ARGUMENTS  {} 
--#SEVERITY   INFORMATIONAL 

::= 2912001 
 
 -- FRU Activation Requested 
trapFRUActivationRequested TRAP-TYPE 
ENTERPRISE petevts 
DESCRIPTION  
 "FRU Activation Requested" 

--#TYPE       "FRU State Event" 
--#SUMMARY    "FRU Activation Requested" 
--#ARGUMENTS  {} 
--#SEVERITY   INFORMATIONAL 

::= 2912002 
 
 -- FRU Not Installed 
trapFRUActivationInProgress TRAP-TYPE 
ENTERPRISE petevts 
DESCRIPTION  
 "FRU Activation In Progress" 

--#TYPE       "FRU State Event" 
--#SUMMARY    "FRU Activation In Progress" 
--#ARGUMENTS  {} 
--#SEVERITY   INFORMATIONAL 

::= 2912003 
 
 -- FRU Active 
trapFRUActive TRAP-TYPE 
ENTERPRISE petevts 
DESCRIPTION  
 "FRU Active" 

--#TYPE       "FRU State Event" 
--#SUMMARY    "FRU Active" 
--#ARGUMENTS  {} 
--#SEVERITY   INFORMATIONAL 

::= 2912004 
 
 -- FRU Deactivation Requested 
trapFRUDeactivationRequested TRAP-TYPE 
ENTERPRISE petevts 
DESCRIPTION  
 "FRU Deactivation Requested" 

--#TYPE       "FRU State Event" 
--#SUMMARY    "FRU Deactivation Requested" 
--#ARGUMENTS  {} 
--#SEVERITY   INFORMATIONAL 

::= 2912005 
 
 -- FRU Deactivation In Progress 
trapFRUDeactivationInProgress TRAP-TYPE 
ENTERPRISE petevts 
DESCRIPTION  
 "FRU Deactivation In Progress" 

--#TYPE       "FRU State Event" 
--#SUMMARY    "FRU Deactivation In Progress" 
--#ARGUMENTS  {} 
--#SEVERITY   INFORMATIONAL 

::= 2912006 
 
 -- FRU Communication Lost 
trapFRUCommunicationLost TRAP-TYPE 
ENTERPRISE petevts 
DESCRIPTION  
 "FRU Communication Lost" 

--#TYPE       "FRU State Event" 
--#SUMMARY    "FRU Communication Lost" 
--#ARGUMENTS  {} 
--#SEVERITY   INFORMATIONAL 

::= 2912007 

--20141021 << 
 -- MEM Status 
--cpu0 ch0
trapMemErrorCPU0CH0DIMM0 TRAP-TYPE 
ENTERPRISE petevts 
DESCRIPTION  
 "CPU0 Channel0 Dimm0 memory Error" 

::= 12873728 

trapMemErrorCPU0CH0DIMM1 TRAP-TYPE 
ENTERPRISE petevts 
DESCRIPTION  
 "CPU0 Channel0 Dimm1 memory Error"
::= 12873729

trapMemErrorCPU0CH0DIMM2 TRAP-TYPE 
ENTERPRISE petevts 
DESCRIPTION  
 "CPU0 Channel0 Dimm2 memory Error" 
::= 12873730

--cpu0 ch1
trapMemErrorCPU0CH1DIMM0 TRAP-TYPE 
ENTERPRISE petevts 
DESCRIPTION  
 "CPU0 Channel1 Dimm0 memory Error" 
::= 12873732 

trapMemErrorCPU0CH1DIMM1 TRAP-TYPE 
ENTERPRISE petevts 
DESCRIPTION  
 "CPU0 Channel1 Dimm1 memory Error" 

::= 12873733

trapMemErrorCPU0CH1DIMM2 TRAP-TYPE 
ENTERPRISE petevts 
DESCRIPTION  
 "CPU0 Channel1 Dimm2 memory Error" 
::= 12873734

--cpu0 ch2
trapMemErrorCPU0CH2DIMM0 TRAP-TYPE 
ENTERPRISE petevts 
DESCRIPTION  
 "CPU0 Channel2 Dimm0 memory Error" 
::= 12873736 

trapMemErrorCPU0CH2DIMM1 TRAP-TYPE 
ENTERPRISE petevts 
DESCRIPTION  
 "CPU0 Channel2 Dimm1 memory Error" 
::= 12873737

trapMemErrorCPU0CH2DIMM2 TRAP-TYPE 
ENTERPRISE petevts 
DESCRIPTION  
 "CPU0 Channel2 Dimm2 memory Error" 
::= 12873738


--cpu0 ch3
trapMemErrorCPU0CH3DIMM0 TRAP-TYPE 
ENTERPRISE petevts 
DESCRIPTION  
 "CPU0 Channel3 Dimm0 memory Error" 
::= 12873740 

END
